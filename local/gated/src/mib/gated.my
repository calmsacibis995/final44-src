GATED-MIB DEFINITIONS ::= BEGIN
 
     IMPORTS
             enterprises
                     FROM RFC1155-SMI
             OBJECT-TYPE
                     FROM RFC-oooo
             TRAP-TYPE
                     FROM RFC-tttt;
 
     --  This MIB module uses the extended OBJECT-TYPE macro as
     --  defined in [9], and the TRAP-TYPE macro as defined in [10]
 
 
     --  Title
 
     gated   OBJECT IDENTIFIER ::= { enterprises 51 }
 
 
 
         gatedAgents OBJECT-TYPE
             SYNTAX   ObjectID
             ACCESS   read-only
             STATUS   mandatory
             DESCRIPTION
                "The SMUX agents group"
            REFERENCE
               "gated.rf 6.1"
           ::= { gated 1 }
 
 
 
 
 
 
 
 
 
 
 
 
 
 
 
 
 
 
 
 
     --  Gated general group
 
     -- Gated general group
 
     gatedGeneralGroup OBJECT IDENTIFIER ::= { gated 2 }
 
 
         gatedGeneralVersion OBJECT-TYPE
             SYNTAX   DisplayString
             ACCESS   read-only
             STATUS   mandatory
             DESCRIPTION
                "The version identification of this instance of
                gated."
            ::= { gatedGeneralGroup 1 }
 
 
 
         gatedGeneralUptime OBJECT-TYPE
             SYNTAX   TimeTicks
             ACCESS   read-only
             STATUS   mandatory
             DESCRIPTION
                "The time in seconds since  the  gated  process
                was started."
            ::= { gatedGeneralGroup 2 }
 
 
 
         gatedGeneralKernelVersion OBJECT-TYPE
             SYNTAX   DisplayString
             ACCESS   read-only
             STATUS   mandatory
             DESCRIPTION
                "The idenification string gated read  from  the
                kernel, usually _version."
            ::= { gatedGeneralGroup 3 }
 
 
 
 
 
 
 
 
 
 
 
 
 
 
 
         gatedGeneralBuildDate OBJECT-TYPE
             SYNTAX   DisplayString
             ACCESS   read-only
             STATUS   mandatory
             DESCRIPTION
                "The date and time this version  of  gated  was
                compiled."
            ::= { gatedGeneralGroup 4 }
 
 
 
 
 
 
 
 
 
 
 
 
 
 
 
 
 
 
 
 
 
 
 
 
 
 
 
 
 
 
 
 
 
 
 
 
 
 
 
 
 
 
 
 
     --  Inet group
 
     -- Variables specific to the Internet protocols supported by gated.
 
     gatedInetGroup OBJECT IDENTIFIER ::= { gated 3 }
 
 
         gatedInetAs OBJECT-TYPE
             SYNTAX   INTEGER
             ACCESS   read-write
             STATUS   mandatory
             DESCRIPTION
                "The autonomous system  this  router  of  which
                this router is a member."
            ::= { gatedInetGroup 1 }
 
 
 
         gatedInetRouterId OBJECT-TYPE
             SYNTAX   IpAddress
             ACCESS   read-write
             STATUS   mandatory
             DESCRIPTION
                "A unique identifier for this router.  Must  be
                the  address  of one of the interfaces attached
                to this router. Used by OSPF as the  Router  ID
                and by BGP as the BGP Identifier."
            ::= { gatedInetGroup 2 }
 
 
 
 
 
 
 
 
 
 
 
 
 
 
 
 
 
 
 
 
 
 
 
 
     --  Gated configuration group
 
     -- This group describes the gated configuration file.
 
     gatedConfigGroup OBJECT IDENTIFIER ::= { gated 4 }
 
 
         gatedConfigTime OBJECT-TYPE
             SYNTAX   TimeTicks
             ACCESS   read-only
             STATUS   mandatory
             DESCRIPTION
                "The interval since gated  was  last  reconfig-
                ured."
            DEFVAL { 0 }
            ::= { gatedConfigGroup 1 }
 
 
 
         gatedConfigFile OBJECT-TYPE
             SYNTAX   DisplayString
             ACCESS   read-write
             STATUS   mandatory
             DESCRIPTION
                "The file gated will  read  it's  configuration
                from."
            ::= { gatedConfigGroup 2 }
 
 
 
         gatedConfigTrigger OBJECT-TYPE
             SYNTAX   INTEGER {
                         reconfigure (1)
                      }
             ACCESS   read-write
             STATUS   mandatory
             DESCRIPTION
                "Setting this value  to  reconfigure  (1)  will
                cause  gated  to start the reconfiguration pro-
                cess."
            DEFVAL { 1 }
            ::= { gatedConfigGroup 3 }
 
 
 
 
 
 
 
 
 
 
     END
