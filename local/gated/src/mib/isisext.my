RFCxxxx-MIB DEFINITIONS ::= BEGIN

          IMPORTS
             experimental, Counter, IpAddress
                FROM RFC1155-SMI -- [4]
             OBJECT-TYPE
                FROM RFC-1212; -- reference [3]

          -- This MIB definition uses the extended OBJECT-TYPE macro
          -- defined in [3]

          -- Title
                isis OBJECT IDENTIFIER ::= { experimental 37 }

          -- OBJECT IDENTIFIER definitions

             isisSystem OBJECT IDENTIFIER ::= { isis 1 }
             isisCirc OBJECT IDENTIFIER ::= { isis 2 }
             isisISAdj OBJECT IDENTIFIER ::= { isis 3 }
             isisESAdj OBJECT IDENTIFIER ::= { isis 4 }
             isisReachAddr OBJECT IDENTIFIER ::= { isis 5 }
             isisIPReachAddr OBJECT IDENTIFIER ::= { isis 6 }
             isisCLNPDest OBJECT IDENTIFIER ::= { isis 7 }
             isisIPDest OBJECT IDENTIFIER ::= { isis 8 }
	  -- Extension
	     isisTest OBJECT IDENTIFIER ::= { isis 9 }

          -- Type definitions

             OSINSAddress ::= OCTET STRING (SIZE(0..20))
                -- OSI Network Service Address, e.g. NSAP,
                -- Network Entity Title

             SNPAAddress ::= OCTET STRING (SIZE(0..20))
                -- A MAC Address or DTE Address or other SNPA Address

             NSAPPrefix ::= OCTET STRING (SIZE(1..21))
                -- NSAP Prefix. The first octet of the string is used to
                -- encode as an unsigned integer the length in bits of the
                -- subsequent prefix. This length must be a multiple of 4
                -- bits and may range from 0..160. The second and
                -- subsequent octets are used to hold the prefix value.
                -- If the last 4 bits of the last octet are not part of
                -- the prefix then their value is undefined.

             SNPAPrefix ::= OCTET STRING (SIZE(1..21))
                -- SNPA Prefix. The first octet of the string is used to
                -- encode as an unsigned integer the length in bits of the
                -- subsequent prefix. The second and
                -- subsequent octets are used to hold the prefix value.
                -- Bits in the last octet which are not part of
                -- the prefix have undefined value.

             SystemID ::= OCTET STRING (SIZE(0..8))
                -- A system ID.

             ExistState ::= INTEGER
                               {
                                  off(1),
                                  on(2)
                               }
                -- Type used in row creation and deletion.

             OperState ::= INTEGER
                               {
                                  off(1),
                                  on(2)
                               }
                -- Type used in enabling and disabling a row.

             LSPBuffSize ::= INTEGER (512..1492)
                -- Integer sub range for LSP size.

             LevelState ::= INTEGER
                               {
                                  off (1),
                                  on (2),
                                  waiting (3)
                               }
                -- states of the ISIS protocol.

             Password ::= OCTET STRING (SIZE(0..254))
                -- Password type used by authentication.

             SupportedProtocol ::= INTEGER
                                     {
                                        iso8473(129),
                                        ip(204)
                                     }
                -- Types of network protocol supported by Integrated ISIS.
                -- The values for ISO8473 and IP are those registered for
                -- these protocols in ISO TR9577.

             DefaultMetric ::= INTEGER (1..63)
                -- Integer sub-range for default metric for single hop.

             OtherMetric ::= INTEGER (0..63)
                -- Integer sub-range for metrics other than the default
                -- meric for single hop.

             MetricType ::= INTEGER
                               {
                                  internal(1),
                                  external(2)
                               }
                -- Class of metric at Level 2.

             PathCost ::= INTEGER (0..1023)
                -- Integer sub-range for any metric for complete path.

             Boolean ::= INTEGER
                            {
                               false (1),
                               true (2)
                            }

             CircuitID ::= OCTET STRING (SIZE(2..9))
                -- ID for a circuit.

             ISPriority ::= INTEGER (1..127)
                -- Integer sub-range for ISIS priority.

             TOS ::= INTEGER
                         {
                            default(1),
                            delay(2),
                            expense(3),
                            error(4)
                         }
                -- Types Of Service (equivalent to Qualities Of Service)
                -- which define types of metric.

          -- Behaviour Definitions


          -- ResettingTimer behaviour definition

          -- "This object specifies the interval between certain events in
          -- the operation of the protocol state machine. If the value of
          -- this object is set to a new value while the protocol state
          -- machine is in operation, the implementation shall take the
          -- necessary steps to ensure that for any time interval which
          -- was in progress when the value of the corresponding object
          -- was changed, the next expiration of that interval takes place
          -- the specified time after the original start of that interval,
          -- or immediately, whichever is later. The precision with which
          -- this time shall be implemented shall be the same as that
          -- associated with the basic operation of the timer object."


          -- ResourceLimiting behaviour definition

          -- "This object places limits on some "resource". In general,
          -- implementations may allocate resources up to this limit when
          -- the object is enabled and it may be impossible to change the
          -- allocation without first disabling and subsequently
          -- re-enabling the object (here disabling and enabling the
          -- object means that the operational state object associated
          -- with the resource limiting object is set to off and on
          -- respectively). It is only required that the value of the
          -- object be settable when the object is disabled. However, some
          -- implementations may be able to change the allocation of the
          -- resource while the object is enabled. In this case it is
          -- always permitted to increase the value of the object at any
          -- time, but it shall not be decreased below the currently
          -- "used" value of the resource."


          -- ExistenceState behaviour definition

          -- "This object controls the creation and deletion of the
          -- corresponding table row. Setting this object to the value off
          -- has the effect of invalidating the corresponding row. It is
          -- an implementation-specific matter whether the agent removes
          -- an invalidated row from a table. Accordingly, management
          -- stations must be prepared to receive tabular information from
          -- agents that corresponds to rows not currently valid. Setting
          -- the value of this object to the same value as its current
          -- value has no effect. If the table entry also contains an
          -- object controlling the operational state of a row (which
          -- follows the operationalState behaviour) then the object
          -- following the existenceState behaviour shall not be set to
          -- off when the object following the operationalState behaviour
          -- has value on. An attempt to do so is rejected."


          -- OperationalState behaviour definition

          -- "This object controls the enabling and disabling of the
          -- corresponding table row. Setting this object to the value
          -- off has the effect of disabling the corresponding row.
          -- Setting this object to the value on has the effect of
          -- enabling the corresponding row. Setting the value of this
          -- object to the same value as its current value has no effect.
          -- If the table entry also contains an object controlling the
          -- existence state of a row (which follows the existenceState
          -- behaviour) then the object following the operationalState
          -- behaviour shall not be set to on when the object following
          -- the existenceState behaviour has value off. An attempt to do
          -- so is rejected.


          -- ReplaceOnlyWhileDisabled behaviour definition

          -- "This object shall only be set when the corresponding row is
          -- disabled (has the value off for the corresponding operational
          -- state object)."


          -- ReplaceOnlyWhileInstanceDisabled behaviour definition

          -- "This object shall only be set when the corresponding row in
          -- the isisSysTable has isisSysOperState set to Off."


          -- Index behaviour definition

          -- "This object is an index object for the table entry. As such
          -- it can only be set to the value which is the same as that
          -- implicit in the Object Identifier value for the instance of
          -- this object."


          -- ManualOrAutomatic behaviour definition

          -- "The access of this object is read-write if the row to which
          -- it belongs is manual (i.e. is being or was created manually)
          -- otherwise (i.e. was created automatically) it is read-only."





          -- The System Group

          -- The System Group is mandatory


          -- The System Table

          -- The System Table contains one row for each separate instance
          -- of the Integrated IS-IS protocol.

          isisSysTable OBJECT-TYPE
             SYNTAX SEQUENCE OF IsisSysEntry
             ACCESS not-accessible
             STATUS mandatory
             DESCRIPTION
                 "The set of instances of the Integrated IS-IS protocol
                 existing on the system."
             ::= { isisSystem 1 }

          isisSysEntry OBJECT-TYPE
             SYNTAX IsisSysEntry
             ACCESS not-accessible
             STATUS mandatory
             DESCRIPTION
                 "Each row defines information specific to a single
                 instance of the protocol existing on the system."
             REFERENCE "{ISIS.poi cLNSISISBasic-P (1)}"
             INDEX { isisSysInstance }
             ::= { isisSysTable 1 }

          IsisSysEntry ::=
             SEQUENCE {
                isisSysInstance
                   INTEGER,
                isisSysExistState
                   ExistState,
                isisSysVersion
                   OCTET STRING,
                isisSysType
                   INTEGER,
                isisSysID
                   SystemID,
                isisSysMaxPathSplits
                   INTEGER,
                isisSysMinLSPTransInt
                   INTEGER,
                isisSysMaxLSPGenInt
                   INTEGER,
                isisSysMinBroadLSPTransInt
                   INTEGER,
                isisSysCompSNPInt
                   INTEGER,
                isisSysOrigL1LSPBuffSize
                   LSPBuffSize,
                isisSysMaxAreaAddresses
                   INTEGER,
                isisSysMinLSPGenInt
                   INTEGER,
                isisSysPollESHelloRate
                   INTEGER,
                isisSysPartSNPInt
                   INTEGER,
                isisSysWaitTime
                   INTEGER,
                isisSysDRISISHelloTimer
                   INTEGER,
                isisSysOperState
                   OperState,
                isisSysL1State
                   LevelState,
                isisSysCorrLSPs
                   Counter,
                isisSysLSPL1DbaseOloads
                   Counter,
                isisSysManAddrDropFromAreas
                   Counter,
                isisSysAttmptToExMaxSeqNums
                   Counter,
                isisSysSeqNumSkips
                   Counter,
                isisSysOwnLSPPurges
                   Counter,
                isisSysIDFieldLenMismatches
                   Counter,
                isisSysMaxAreaAddrMismatches
                   Counter,
                isisSysOrigL2LSPBuffSize
                   LSPBuffSize,
                isisSysL2State
                   LevelState,
                isisSysLSPL2DbaseOloads
                   Counter,
                isisSysAuthAreaTransPwd
                   Password,
                isisSysAuthDomainTransPwd
                   Password,
                isisSysAuthFails
                   Counter
             }

          isisSysInstance OBJECT-TYPE
             SYNTAX INTEGER
             ACCESS read-write
             STATUS mandatory
             DESCRIPTION
                 "The unique identifier of the Integrated IS-IS instance
                 to which this row corresponds. This object follows the
                 index behaviour."
             ::= { isisSysEntry 1 }

          isisSysExistState OBJECT-TYPE
             SYNTAX ExistState
             ACCESS read-write
             STATUS mandatory
             DESCRIPTION
                 "The validity of this instance of the Integrated IS-IS
                 protocol. This object follows the existenceState
                 behaviour."
             DEFVAL { on }				-- 02new
             ::= { isisSysEntry 2 }

          isisSysVersion OBJECT-TYPE
             SYNTAX OCTET STRING
             ACCESS read-only
             STATUS mandatory
             DESCRIPTION
                 "The version number of the IS-IS protocol to which this
                 instance conforms. This value must be set by the
                 implementation when the row is valid."
             REFERENCE "{ISIS.aoi version (1)}"
             ::= { isisSysEntry 3 }

          isisSysType OBJECT-TYPE
             SYNTAX   INTEGER {
                         level1IS (1),
                         level2IS (2)
                      }
             ACCESS read-write
             STATUS mandatory
             DESCRIPTION
                 "The type of this instance of the Integrated IS-IS
                 protocol. This object follows the
                 replaceOnlyWhileDisabled behaviour."
             REFERENCE "{ISIS.aoi iSType (2)}"
             ::= { isisSysEntry 4 }

          isisSysID OBJECT-TYPE
             SYNTAX SystemID
             ACCESS read-write
             STATUS mandatory
             DESCRIPTION
                 "The ID for this instance of the Integrated IS-IS
                 protocol. This value is appended to each of the
                 instance's area addresses to form the Network Entity
                 Titles valid for this instance. The derivation of a value
                 for this object is implementation-specific. Some
                 implementations may assign values and not permit write
                 access, others may require the value to be set manually."
             REFERENCE "{ISIS.aoi systemId (119)}"
             ::= { isisSysEntry 5 }

          isisSysMaxPathSplits OBJECT-TYPE
             SYNTAX INTEGER (1..32)
             ACCESS read-write
             STATUS mandatory
             DESCRIPTION
                 "Maximum number of paths with equal routing metric value
                 which it is permitted to split between. This object
                 follows the replaceOnlyWhileDisabled behaviour."
             REFERENCE "{ISIS.aoi maximumPathSplits (3)}"
             DEFVAL { 2 }
             ::= { isisSysEntry 6 }

          isisSysMinLSPTransInt OBJECT-TYPE
             SYNTAX INTEGER (1..65535)
             ACCESS read-write
             STATUS mandatory
             DESCRIPTION
                 "Minimum interval, in seconds, between re-transmission of
                 an LSP. This object follows the resettingTimer
                 behaviour."
             REFERENCE "{ISIS.aoi minimumLSPTransmissionInterval (5)}"
             DEFVAL { 5 }
             ::= { isisSysEntry 7 }

          isisSysMaxLSPGenInt OBJECT-TYPE
             SYNTAX INTEGER (1..65535)
             ACCESS read-write
             STATUS mandatory
             DESCRIPTION
                 "Maximum interval, in seconds, between generated LSPs by
                 this instance. This object follows the resettingTimer
                 behaviour."
             REFERENCE "{ISIS.aoi maximumLSPGenerationInterval (6)}"
             DEFVAL { 900 }
             ::= { isisSysEntry 8 }

          isisSysMinBroadLSPTransInt OBJECT-TYPE
             SYNTAX INTEGER (1..65535)
             ACCESS read-write
             STATUS mandatory
             DESCRIPTION
                 "Minimum interval, in milliseconds, between transmission
                 of LSPs on a broadcast circuit. This object follows the
                 resettingTimer behaviour. This timer shall be capable of
                 a resolution not coarser than 10 milliseconds."
             REFERENCE "{ISIS.aoi
                minimumBroadcastLSPTransmissionInterval (7)}"
             DEFVAL { 33 }
             ::= { isisSysEntry 9 }

          isisSysCompSNPInt OBJECT-TYPE
             SYNTAX INTEGER (1..600)
             ACCESS read-write
             STATUS mandatory
             DESCRIPTION
                 "Interval, in seconds, between generation of Complete
                 Sequence Numbers PDUs by a designated Intermediate System
                 on a broadcast circuit. This object follows the
                 resettingTimer behaviour."
             REFERENCE "{ISIS.aoi completeSNPInterval (8)}"
             DEFVAL { 10 }
             ::= { isisSysEntry 10 }

          isisSysOrigL1LSPBuffSize OBJECT-TYPE
             SYNTAX LSPBuffSize
             ACCESS read-only
             STATUS mandatory
             DESCRIPTION
                 "The maximum size of Level 1 LSPs and SNPs originated by
                 this instance. This object follows the
                 replaceOnlyWhileDisabled behaviour."
             REFERENCE "{ISIS.aoi originatingL1LSPBufferSize (9)}"
             DEFVAL { 1492 }
             ::= { isisSysEntry 11 }

          isisSysMaxAreaAddresses OBJECT-TYPE
             SYNTAX INTEGER(0..254)
             ACCESS read-write
             STATUS mandatory
             DESCRIPTION
                 "The maximum number of area addresses to be permitted for
                 the area in which this instance exists. Note that all
                 Intermediate Systems in the same area must have the same
                 value configured for this attribute if correct operation
                 is to be assumed. This object follows the
                 replaceOnlyWhileDisabled behaviour."
             REFERENCE "{ISIS.aoi maximumAreaAddresses (4)}"
             DEFVAL { 3 }
             ::= { isisSysEntry 12 }

          isisSysMinLSPGenInt OBJECT-TYPE
             SYNTAX INTEGER (1..65535)
             ACCESS read-write
             STATUS mandatory
             DESCRIPTION
                 "Minimum interval, in seconds, between successive
                 generation of LSPs with the same LSPID by this instance.
                 This object follows the resettingTimer behaviour."
             REFERENCE "{ISIS.aoi minimumLSPGenerationInterval (11)}"
             DEFVAL { 30 }
             ::= { isisSysEntry 13 }

          isisSysPollESHelloRate OBJECT-TYPE
             SYNTAX INTEGER (1..65535)
             ACCESS read-write
             STATUS mandatory
             DESCRIPTION
                 "The value, in seconds, to be used for the suggested ES
                 configuration  timer in ISH PDUs when soliciting the ES
                 configuration."
             REFERENCE "{ISIS.aoi pollESHelloRate (13)}"
             DEFVAL { 50 }
             ::= { isisSysEntry 14 }

          isisSysPartSNPInt OBJECT-TYPE
             SYNTAX INTEGER (1..65535)
             ACCESS read-write
             STATUS mandatory
             DESCRIPTION
                 "Minimum interval between sending Partial Sequence Number
                 PDUs. This object follows the resettingTimer behaviour."
             REFERENCE "{ISIS.aoi partialSNPInterval (14)}"
             DEFVAL { 2 }
             ::= { isisSysEntry 15 }

          isisSysWaitTime OBJECT-TYPE
             SYNTAX INTEGER (1..65535)
             ACCESS read-write
             STATUS mandatory
             DESCRIPTION
                 "Number of seconds to delay in waiting state before
                 entering on state. This object follows the resettingTimer
                 behaviour."
             REFERENCE "{ISIS.aoi waitingTime (15)}"
             DEFVAL { 60 }
             ::= { isisSysEntry 16 }

          isisSysDRISISHelloTimer OBJECT-TYPE
             SYNTAX INTEGER (1..65535)
             ACCESS read-write
             STATUS mandatory
             DESCRIPTION
                 "The interval, in seconds, between the generation of IIH
                 PDUs by the designated IS on a LAN. This object follows
                 the resettingTimer behaviour."
             REFERENCE "{ISIS.aoi dRISISHelloTimer (16)}"
             DEFVAL { 1 }
             ::= { isisSysEntry 17 }

          isisSysOperState OBJECT-TYPE
             SYNTAX OperState
             ACCESS read-write
             STATUS mandatory
             DESCRIPTION
                 "The operational state of this instance of the Integrated
                 IS-IS protocol. Setting this object to the value on when
                 its current value is off enables operation of this
                 instance of the Integrated IS-IS protocol."
             DEFVAL { off }
             ::= { isisSysEntry 18 }

          isisSysL1State OBJECT-TYPE
             SYNTAX LevelState
             ACCESS read-only
             STATUS mandatory
             DESCRIPTION
                 "The state of the Level 1 database."
             REFERENCE "{ISIS.aoi l1State (17)}"
             ::= { isisSysEntry 19 }

          isisSysCorrLSPs OBJECT-TYPE
             SYNTAX Counter
             ACCESS read-only
             STATUS mandatory
             DESCRIPTION
                 "Number of corrupted LSPs detected."
             REFERENCE "{ISIS.aoi corruptedLSPsDetected (19)}"
             ::= { isisSysEntry 20 }

          isisSysLSPL1DbaseOloads OBJECT-TYPE
             SYNTAX Counter
             ACCESS read-only
             STATUS mandatory
             DESCRIPTION
                 "Number of times the LSP L1 database has become
                 overloaded."
             REFERENCE "{ISIS.aoi lSPL1DatabaseOverloads (20)}"
             ::= { isisSysEntry 21 }

          isisSysManAddrDropFromAreas OBJECT-TYPE
             SYNTAX Counter
             ACCESS read-only
             STATUS mandatory
             DESCRIPTION
                 "Number of times a manual address has been dropped from
                 the area."
             REFERENCE "{ISIS.aoi manualAddressesDroppedFromArea (21)}"
             ::= { isisSysEntry 22 }

          isisSysAttmptToExMaxSeqNums OBJECT-TYPE
             SYNTAX Counter
             ACCESS read-only
             STATUS mandatory
             DESCRIPTION
                 "Number of times the IS has attempted to exceed the
                 maximum sequence number."
             REFERENCE "{ISIS.aoi
                         attemptsToExceedmaximumSequenceNumber (22)}"
             ::= { isisSysEntry 23 }

          isisSysSeqNumSkips OBJECT-TYPE
             SYNTAX Counter
             ACCESS read-only
             STATUS mandatory
             DESCRIPTION
                 "Number of times a sequence number skip has occurred."
             REFERENCE "{ISIS.aoi sequenceNumberSkips (23)}"
             ::= { isisSysEntry 24 }

          isisSysOwnLSPPurges OBJECT-TYPE
             SYNTAX Counter
             ACCESS read-only
             STATUS mandatory
             DESCRIPTION
                 "Number of times a zero-aged copy of the system's own LSP
                 is received from some other node."
             REFERENCE "{ISIS.aoi ownLSPPurges (24)}"
             ::= { isisSysEntry 25 }

          isisSysIDFieldLenMismatches OBJECT-TYPE
             SYNTAX Counter
             ACCESS read-only
             STATUS mandatory
             DESCRIPTION
                 "Number of times a PDU is received with a different value
                 for ID field length to that of the receiving system."
             REFERENCE "{ISIS.aoi iDFieldLengthMismatches (25)}"
             ::= { isisSysEntry 26 }

          isisSysMaxAreaAddrMismatches OBJECT-TYPE
             SYNTAX Counter
             ACCESS read-only
             STATUS mandatory
             DESCRIPTION
                 "Number of times a PDU is received with a different value
                 for MaximumAreaAddresses from that of the receiving
                 system."
             REFERENCE "{ISIS.aoi MaximumAreaAddressesMismatches (118)}"
             ::= { isisSysEntry 27 }

          -- The following objects map those from the cLNSISISLevel2-P
          -- Package

          isisSysOrigL2LSPBuffSize OBJECT-TYPE
             SYNTAX LSPBuffSize
             ACCESS read-write
             STATUS mandatory
             DESCRIPTION
                 "The maximum size of Level 2 LSPs and SNPs originated by
                 this system. This object follows the
                 replaceOnlyWhileDisabled behaviour."
             REFERENCE "{ISIS.aoi originatingL2LSPBufferSize (26)}"
             DEFVAL { 1492 }
             ::= { isisSysEntry 28 }

          isisSysL2State OBJECT-TYPE
             SYNTAX LevelState
             ACCESS read-only
             STATUS mandatory
             DESCRIPTION
                 "The state of the Level 2 database."
             REFERENCE "{ISIS.aoi l2State (28)}"
             ::= { isisSysEntry 29 }

          isisSysLSPL2DbaseOloads OBJECT-TYPE
             SYNTAX Counter
             ACCESS read-only
             STATUS mandatory
             DESCRIPTION
                 "Number of times the Level 2 LSP database has become
                 overloaded."
             REFERENCE "{ISIS.aoi lSPL2DatabaseOverloads (32)}"
             ::= { isisSysEntry 30 }

          -- The following objects map some of those from the
          -- cLNSISISAuthentication-P and cLNSISISLevel2Authentication-P
          -- packages

          isisSysAuthAreaTransPwd OBJECT-TYPE
             SYNTAX Password
             ACCESS read-write
             STATUS mandatory
             DESCRIPTION
                 "The value to be used as the transmit password in Level 1
                 LSP and SNP PDUs generated by this instance of the
                 protocol. If the value of this object is ''H, the zero
                 length octet string, then the authentication option is
                 not included in Level 1 LSP and SNP PDUs generated by
                 this instance of the protocol."
             REFERENCE "{ISIS.aoi areaTransmitPassword (111)}"
             DEFVAL { ''H } -- the zero length octet string.
             ::= { isisSysEntry 31 }

          isisSysAuthDomainTransPwd OBJECT-TYPE
             SYNTAX Password
             ACCESS read-write
             STATUS mandatory
             DESCRIPTION
                 "The value to be used as the transmit password in Level 2
                 LSP and SNP PDUs generated by this instance of the
                 protocol. If the value of this object is ''H, the zero
                 length octet string, then the authentication option is
                 not included in Level 2 LSP and SNP PDUs generated by
                 this instance of the protocol."
             REFERENCE "{ISIS.aoi domainTransmitPassword (113)}"
             DEFVAL { ''H } -- the zero length octet string.
             ::= { isisSysEntry 32 }

          isisSysAuthFails OBJECT-TYPE
             SYNTAX Counter
             ACCESS read-only
             STATUS mandatory
             DESCRIPTION
                 "The number of authentication failures recognized by this
                 instance of the protocol."
             REFERENCE "{ISIS.aoi authenticationFailures (117)}"
             ::= { isisSysEntry 33 }


          -- The Level 1 Manual Area Address Table

          -- The Level 1 Manual Area Address Table
          -- contains the set of area addresses manually configured
          -- for each instance of the Integrated IS-IS protocol.

          -- At least one row in which the value of
          -- isisManAreaAddrExistState
          -- is on must be present for each instance of the protocol
          -- when isisSysOperState is also on for that instance. The
          -- maximum number of rows in this table for each instance of
          -- the protocol for which the object isisManAreaAddrExistState
          -- has the value on is the value of maximumAreaAddresses (as
          -- defined in ISO 10589) for that instance. An Attempt
          -- to create a new row such that the number of rows with
          -- isisManAreaAddrExistState set to on for that protocol
          -- instance exceeds maximumAreaAddresses is rejected."

          isisManAreaAddrTable OBJECT-TYPE
             SYNTAX SEQUENCE OF IsisManAreaAddrEntry
             ACCESS not-accessible
             STATUS mandatory
             DESCRIPTION
                 "The set of manual area addresses configured on this
                 Intermediate System."
             REFERENCE "{ISIS.aoi manualAreaAddresses (10)}"
             ::= { isisSystem 2 }

          isisManAreaAddrEntry OBJECT-TYPE
             SYNTAX IsisManAreaAddrEntry
             ACCESS not-accessible
             STATUS mandatory
             DESCRIPTION
                 "Each entry contains one area address manually configured
                 on this system"
             INDEX {  isisManAreaAddrSysInstance,
                      isisManAreaAddr }
             ::= { isisManAreaAddrTable 1 }

          IsisManAreaAddrEntry ::=
             SEQUENCE {
                isisManAreaAddrSysInstance
                   INTEGER,
                isisManAreaAddr
                   OSINSAddress,
                isisManAreaAddrExistState
                   ExistState
             }

          isisManAreaAddrSysInstance OBJECT-TYPE
             SYNTAX INTEGER
             ACCESS read-write
             STATUS mandatory
             DESCRIPTION
                 "The unique identifier of the Integrated IS-IS instance
                 to which this row corresponds. This object follows the
                 index behaviour."
             ::= { isisManAreaAddrEntry 1 }

          isisManAreaAddr OBJECT-TYPE
             SYNTAX OSINSAddress
             ACCESS read-write
             STATUS mandatory
             DESCRIPTION
                 "A manually configured area address for this system. This
                 object follows the index behaviour."
             ::= { isisManAreaAddrEntry 2 }

          isisManAreaAddrExistState OBJECT-TYPE
             SYNTAX ExistState
             ACCESS read-write
             STATUS mandatory
             DESCRIPTION
                 "The state of the isisManAreaAddrEntry. This object
                 follows the ExistenceState behaviour. If an attempt is
                 made to set this object to the value off when the
                 corresponding isisManAreaAddrEntry is the only valid
                 entry for this instance and when the corresponding ISIS
                 instance has isisSysOperState set to On then the attempt
                 is rejected."
             DEFVAL { on }
             ::= { isisManAreaAddrEntry 3 }


          -- The Level 1 Area Address Table

          -- The Level 1 Area Address Table contains the
          -- union of the sets of area addresses reported in all Level 1
          -- LSPs received by this Intermediate System.

          isisAreaAddrTable OBJECT-TYPE
             SYNTAX SEQUENCE OF IsisAreaAddrEntry
             ACCESS not-accessible
             STATUS mandatory
             DESCRIPTION
                 "The union of the sets of area addresses reported in all
                 Level 1 LSPs received by this instance of the protocol."
             REFERENCE "{ISIS.aoi areaAddresses (18)}"
             ::= { isisSystem 3 }

          isisAreaAddrEntry OBJECT-TYPE
             SYNTAX IsisAreaAddrEntry
             ACCESS not-accessible
             STATUS mandatory
             DESCRIPTION
                 "Each entry contains one area address reported in a
                 Level 1 LSP received by this instance of the protocol."
             INDEX {  isisAreaAddrSysInstance,
                      isisAreaAddr }
             ::= { isisAreaAddrTable 1 }

          IsisAreaAddrEntry ::=
             SEQUENCE {
                isisAreaAddrSysInstance
                   INTEGER,
                isisAreaAddr
                   OSINSAddress
             }

          isisAreaAddrSysInstance OBJECT-TYPE
             SYNTAX INTEGER
             ACCESS read-only
             STATUS mandatory
             DESCRIPTION
                 "The unique identifier of the Integrated IS-IS instance
                 to which this row corresponds."
             ::= { isisAreaAddrEntry 1 }

          isisAreaAddr OBJECT-TYPE
             SYNTAX OSINSAddress
             ACCESS read-only
             STATUS mandatory
             DESCRIPTION
                 "An area address reported in a Level 1 LSP received by
                 this instance of the protocol."
             ::= { isisAreaAddrEntry 2 }



          -- The System Integrated Group

          -- The System Integrated Group is present if the system
          -- supports Integrated ISIS at Level 1.


          -- The System Protocol Supported Table

          -- The System Protocol Supported Table contains the manually
          -- configured set of protocols supported by each
          -- instance of the Integrated ISIS protocol.

          isisSysProtSuppTable OBJECT-TYPE
             SYNTAX SEQUENCE OF IsisSysProtSuppEntry
             ACCESS not-accessible
             STATUS mandatory
             DESCRIPTION
                 "This table contains the manually configured set of
                 protocols supported by each instance of the Integrated
                 ISIS protocol."
             ::= { isisSystem 4 }

          isisSysProtSuppEntry OBJECT-TYPE
             SYNTAX IsisSysProtSuppEntry
             ACCESS not-accessible
             STATUS mandatory
             DESCRIPTION
                 "Each entry contains one protocol supported by an
                 instance of the Integrated ISIS protocol."
             INDEX {  isisSysProtSuppSysInstance,
                      isisSysProtSuppProtocol }
             ::= { isisSysProtSuppTable 1 }

          IsisSysProtSuppEntry ::=
             SEQUENCE {
                isisSysProtSuppSysInstance
                   INTEGER,
                isisSysProtSuppProtocol
                   SupportedProtocol,
                isisSysProtSuppExistState
                   ExistState
             }

          isisSysProtSuppSysInstance OBJECT-TYPE
             SYNTAX INTEGER
             ACCESS read-write
             STATUS mandatory
             DESCRIPTION
                 "The unique identifier of the Integrated IS-IS instance
                 to which this row corresponds. This object follows the
                 index behaviour."
             ::= { isisSysProtSuppEntry 1 }

          isisSysProtSuppProtocol OBJECT-TYPE
             SYNTAX SupportedProtocol
             ACCESS read-write
             STATUS mandatory
             DESCRIPTION
                 "One supported protocol. This object follows the index
                 behaviour."
             ::= { isisSysProtSuppEntry 2 }

          isisSysProtSuppExistState OBJECT-TYPE
             SYNTAX ExistState
             ACCESS read-write
             STATUS mandatory
             DESCRIPTION
                 "The state of the isisSysProtSuppEntry. This object
                 follows the ExistenceState and
                 ReplaceOnlyWhileInstanceDisabled behaviours."
             DEFVAL { on }
             ::= { isisSysProtSuppEntry 3 }



          -- The Level 2 IP Group

          -- The Level 2 IP Group is present if the system
          -- supports IP Integrated IS-IS at Level 2


          -- The Level 2 Summary Address Table

          -- The Level 2 Summary Address Table contains the set of summary
          -- addresses manually configured for each Level 2 instance of
          -- IP Integrated ISIS on the system.

          isisL2SummAddrTable OBJECT-TYPE
             SYNTAX SEQUENCE OF IsisL2SummAddrEntry
             ACCESS not-accessible
             STATUS mandatory
             DESCRIPTION
                 "The set of IP summary addresses to use in forming the
                 contents of Level 2 LSPs originated by this level 2
                 Intermediate System."
             ::= { isisSystem 5 }

          isisL2SummAddrEntry OBJECT-TYPE
             SYNTAX IsisL2SummAddrEntry
             ACCESS not-accessible
             STATUS mandatory
             DESCRIPTION
                 "Each entry contains one IP summary address."
             INDEX {  isisL2SummAddrSysInstance,
                      isisL2SummAddress,
                      isisL2SummAddrMask }
             ::= { isisL2SummAddrTable 1 }

          IsisL2SummAddrEntry ::=
             SEQUENCE {
                isisL2SummAddrSysInstance
                   INTEGER,
                isisL2SummAddress
                   IpAddress,
                isisL2SummAddrMask
                   IpAddress,
                isisL2SummAddrExistState
                   ExistState,
                isisL2SummAddrOperState
                   OperState,
                isisL2SummAddrDefaultMetric
                   DefaultMetric,
                isisL2SummAddrDelayMetric
                   OtherMetric,
                isisL2SummAddrExpenseMetric
                   OtherMetric,
                isisL2SummAddrErrorMetric
                   OtherMetric
             }

          isisL2SummAddrSysInstance OBJECT-TYPE
             SYNTAX INTEGER
             ACCESS read-write
             STATUS mandatory
             DESCRIPTION
                 "The unique identifier of the Integrated IS-IS instance
                 to which this row corresponds. This object follows the
                 replaceOnlyWhileDisabled and index behaviours."
             ::= { isisL2SummAddrEntry 1 }

          isisL2SummAddress OBJECT-TYPE
             SYNTAX IpAddress
             ACCESS read-write
             STATUS mandatory
             DESCRIPTION
                 "The IP Address value for this summary address. This
                 object follows the index behaviour."
             ::= { isisL2SummAddrEntry 2 }

          isisL2SummAddrMask OBJECT-TYPE
             SYNTAX IpAddress
             ACCESS read-write
             STATUS mandatory
             DESCRIPTION
                 "The mask value for this summary address. This object
                 follows the index behaviour."
             ::= { isisL2SummAddrEntry 3 }

          isisL2SummAddrExistState OBJECT-TYPE
             SYNTAX ExistState
             ACCESS read-write
             STATUS mandatory
             DESCRIPTION
                 "The existence state of this summary address. This object
                 follows the existenceState behaviour."
             DEFVAL { on }
             ::= { isisL2SummAddrEntry 4 }

          isisL2SummAddrOperState OBJECT-TYPE
             SYNTAX OperState
             ACCESS read-write
             STATUS mandatory
             DESCRIPTION
                 "The operational state of this entry. This object follows
                 the operationalState behaviour. When the operational
                 state changes if this would cause the contents of Level 2
                 LSPs originated by the system to change then those new
                 LSPs must be generated and sent as soon as is permitted
                 by the ISIS protocol."
             DEFVAL { off }
             ::= { isisL2SummAddrEntry 5 }

          isisL2SummAddrDefaultMetric OBJECT-TYPE
             SYNTAX DefaultMetric
             ACCESS read-write
             STATUS mandatory
             DESCRIPTION
                 "The default metric value to announce this summary
                 address with in Level 2 LSPs generated by this system."
             DEFVAL { 20 }
             ::= { isisL2SummAddrEntry 6 }

          isisL2SummAddrDelayMetric OBJECT-TYPE
             SYNTAX OtherMetric
             ACCESS read-write
             STATUS mandatory
             DESCRIPTION
                 "The delay metric value to announce this summary address
                 with in Level 2 LSPs generated by this system. The value
                 of zero is reserved to indicate that this metric is not
                 supported."
             DEFVAL { 0 }
             ::= { isisL2SummAddrEntry 7 }

          isisL2SummAddrExpenseMetric OBJECT-TYPE
             SYNTAX OtherMetric
             ACCESS read-write
             STATUS mandatory
             DESCRIPTION
                 "The expense metric value to announce this summary
                 address  with in Level 2 LSPs generated by this system.
                 The value of zero is reserved to indicate that this
                 metric is not supported."
             DEFVAL { 0 }
             ::= { isisL2SummAddrEntry 8 }

          isisL2SummAddrErrorMetric OBJECT-TYPE
             SYNTAX OtherMetric
             ACCESS read-write
             STATUS mandatory
             DESCRIPTION
                 "The error metric value to announce this summary address
                 with in Level 2 LSPs generated by this system. The value
                 of zero is reserved to indicate that this metric is not
                 supported."
             DEFVAL { 0 }
             ::= { isisL2SummAddrEntry 9 }



          -- The Authentication Group

          -- The Authentication Group is present if the authentication
          -- procedures are supported.

          -- This groups maps some of the objects contained in the
          -- cLNSISISAuthentication-P package and the
          -- cLNSISISLevel2Authentication-P package.


          -- The Level 1 Area Receive Password Table

          -- The Level 1 Area Receive Password Table is present
          -- if the Level 1 authentication procedures are supported.
          -- It contains the passwords to use for checking
          -- received Level 1 LSP and SNP PDUs. Note that the set used
          -- for checking also includes the value of the object
          -- isisSysAuthAreaTransPwd but that value is not present in this
          -- table.

          isisAuthAreaRecPwdTable OBJECT-TYPE
             SYNTAX SEQUENCE OF IsisAuthAreaRecPwdEntry
             ACCESS not-accessible
             STATUS mandatory
             DESCRIPTION
                 "The set of passwords to use for checking received Level
                 1 LSP and SNP PDUs."
             REFERENCE "{ISIS.aoi areaReceivePasswords (112)}"
             ::= { isisSystem 6 }

          isisAuthAreaRecPwdEntry OBJECT-TYPE
             SYNTAX IsisAuthAreaRecPwdEntry
             ACCESS not-accessible
             STATUS mandatory
             DESCRIPTION
                 "Each entry contains one password to treat as valid in a
                 received Level 1 LSP or SNP PDU."
             INDEX {  isisAuthAreaRecPwdSysInstance,
                      isisAuthAreaRecPwd }
             ::= { isisAuthAreaRecPwdTable 1 }

          IsisAuthAreaRecPwdEntry ::=
             SEQUENCE {
                isisAuthAreaRecPwdSysInstance
                   INTEGER,
                isisAuthAreaRecPwd
                   Password,
                isisAuthAreaRecPwdExistState
                   ExistState
             }

          isisAuthAreaRecPwdSysInstance OBJECT-TYPE
             SYNTAX INTEGER
             ACCESS read-write
             STATUS mandatory
             DESCRIPTION
                 "The unique identifier of the Integrated IS-IS instance
                 to which this row corresponds. This object follows the
                 index behaviour."
             ::= { isisAuthAreaRecPwdEntry 1 }

          isisAuthAreaRecPwd OBJECT-TYPE
             SYNTAX Password
             ACCESS read-write
             STATUS mandatory
             DESCRIPTION
                 "A password to treat as valid in a received Level 1 LSP
                 or SNP PDU. This object follows the index behaviour."
             ::= { isisAuthAreaRecPwdEntry 2 }

          isisAuthAreaRecPwdExistState OBJECT-TYPE
             SYNTAX ExistState
             ACCESS read-write
             STATUS mandatory
             DESCRIPTION
                 "The existence state of the isisAreaRecPwdEntry. This
                 object follows the existenceState behaviour."
             DEFVAL { on }
             ::= { isisAuthAreaRecPwdEntry 3 }


          -- The Level 2 Domain Receive Password Table

          -- The Level 2 Domain Receive Password Table is present if
          -- the Level 2 authentication procedures are supported.
          -- It contains the passwords to use for checking
          -- received Level 2 LSP and SNP PDUs. Note that the set used
          -- for checking also includes the value of the object
          -- isisSysAuthDomainTransPwd but that value is not present in
          -- this table.

          isisAuthDomainRecPwdTable OBJECT-TYPE
             SYNTAX SEQUENCE OF IsisAuthDomainRecPwdEntry
             ACCESS not-accessible
             STATUS mandatory
             DESCRIPTION
                 "The set of passwords to use for checking received Level
                 2 LSP and SNP PDUs."
             REFERENCE "{ISIS.aoi domainReceivePasswords (114)}"
             ::= { isisSystem 7 }

          isisAuthDomainRecPwdEntry OBJECT-TYPE
             SYNTAX IsisAuthDomainRecPwdEntry
             ACCESS not-accessible
             STATUS mandatory
             DESCRIPTION
                 "Each entry contains one password to treat as valid in a
                 received Level 2 LSP or SNP PDU."
             INDEX {  isisAuthDomainRecPwdSysInstance,
                      isisAuthDomainRecPwd }
             ::= { isisAuthDomainRecPwdTable 1 }

          IsisAuthDomainRecPwdEntry ::=
             SEQUENCE {
                isisAuthDomainRecPwdSysInstance
                   INTEGER,
                isisAuthDomainRecPwd
                   Password,
                isisAuthDomainRecPwdExistState
                   ExistState
             }

          isisAuthDomainRecPwdSysInstance OBJECT-TYPE
             SYNTAX INTEGER
             ACCESS read-write
             STATUS mandatory
             DESCRIPTION
                 "The unique identifier of the Integrated IS-IS instance
                 to which this row corresponds. This object follows the
                 index behaviour."
             ::= { isisAuthDomainRecPwdEntry 1 }

          isisAuthDomainRecPwd OBJECT-TYPE
             SYNTAX Password
             ACCESS read-write
             STATUS mandatory
             DESCRIPTION
                 "A password to treat as valid in a  received Level 2 LSP
                 or SNP PDU. This object follows the index behaviour."
             ::= { isisAuthDomainRecPwdEntry 2 }

          isisAuthDomainRecPwdExistState OBJECT-TYPE
             SYNTAX ExistState
             ACCESS read-write
             STATUS mandatory
             DESCRIPTION
                 "The existence state of the isisDomainRecPwdEntry. This
                 object follows the ExistenceState behaviour."
             DEFVAL { on }
             ::= { isisAuthDomainRecPwdEntry 3 }



          -- The Partition Repair Group

          -- The Partition Repair Group is present if the system supports
          -- the partition repair option.


          -- The Partition Repair Table

          -- The Partition Repair Table contains an entry for each
          -- instance of the protocol for which the Partition Repair
          -- function is implemented.

          isisPartRepTable OBJECT-TYPE
             SYNTAX SEQUENCE OF IsisPartRepEntry
             ACCESS not-accessible
             STATUS mandatory
             DESCRIPTION
                 "The set of entries containing information about the
                 Partition Repair function in each instance of the
                 protocol."
             ::= { isisSystem 8 }

          isisPartRepEntry OBJECT-TYPE
             SYNTAX IsisPartRepEntry
             ACCESS not-accessible
             STATUS mandatory
             DESCRIPTION
                 "Partition Repair function information specific to each
                 instance of the protocol."
             INDEX {  isisPartRepSysInstance }
             ::= { isisPartRepTable 1 }

          IsisPartRepEntry ::=
             SEQUENCE {
                isisPartRepSysInstance
                   INTEGER,
                isisPartRepMaxVirtAdj
                   INTEGER,
                isisPartRepDesL2IS
                   SystemID,
                isisPartRepVirtLinkChgs
                   Counter
             }

          isisPartRepSysInstance OBJECT-TYPE
             SYNTAX INTEGER
             ACCESS read-write
             STATUS mandatory
             DESCRIPTION
                 "The unique identifier of the Integrated IS-IS instance
                 to which this row corresponds. This object follows the
                 index behaviour."
             ::= { isisPartRepEntry 1 }

          isisPartRepMaxVirtAdj OBJECT-TYPE
             SYNTAX INTEGER (0..32)
             ACCESS read-write
             STATUS mandatory
             DESCRIPTION
                 "The maximum number of Virtual Adjacencies which may be
                 created to repair partitioned Level 1 domains."
             REFERENCE "{ISIS.aoi maximumVirtualAdjacencies (27)}"
             DEFVAL { 2 }
             ::= { isisPartRepEntry 2 }

          isisPartRepDesL2IS OBJECT-TYPE
             SYNTAX SystemID
             ACCESS read-only
             STATUS mandatory
             DESCRIPTION
                 "The ID of the Partition Designated Level 2 Intermediate
                 System."
             REFERENCE "{ISIS.aoi
                partitionDesignatedL2IntermediateSystem (30)}"
             ::= { isisPartRepEntry 3 }

          isisPartRepVirtLinkChgs OBJECT-TYPE
             SYNTAX Counter
             ACCESS read-only
             STATUS mandatory
             DESCRIPTION
                 "The number of times a virtual link is either created or
                 deleted."
             REFERENCE "{ISIS.aoi partitionVirtualLinkChanges (31)}"
             ::= { isisPartRepEntry 4 }


          -- The Partition Area Address Table

          -- The Partition Area Address table contains for each instance
          -- of the protocol the set union of
          -- all area addresses of all Intermediate Systems in the
          -- partition reachable by non-virtual links (calculated from
          -- their Level 1 LSPs)

          isisPartAreaAddrTable OBJECT-TYPE
             SYNTAX SEQUENCE OF IsisPartAreaAddrEntry
             ACCESS not-accessible
             STATUS mandatory
             DESCRIPTION
                 "The set union for each protocol instance of the area
                 addresses reported in all Level 1 LSPs in the partition
                 reachable by non-virtual links."
             REFERENCE "{ISIS.aoi partitionAreaAddresses (29)}"
             ::= { isisSystem 9 }

          isisPartAreaAddrEntry OBJECT-TYPE
             SYNTAX IsisPartAreaAddrEntry
             ACCESS not-accessible
             STATUS mandatory
             DESCRIPTION
                 "Each entry contains one area address reported in a
                 Level 1 LSP in a partition reachable by a non-virtual
                 link."
             INDEX {  isisPartAreaAddrSysInstance,
                      isisPartAreaAddr }
             ::= { isisPartAreaAddrTable 1 }

          IsisPartAreaAddrEntry ::=
             SEQUENCE {
                isisPartAreaAddrSysInstance
                   INTEGER,
                isisPartAreaAddr
                   OSINSAddress
             }

          isisPartAreaAddrSysInstance OBJECT-TYPE
             SYNTAX INTEGER
             ACCESS read-only
             STATUS mandatory
             DESCRIPTION
                 "The unique identifier of the Integrated IS-IS instance
                 to which this row corresponds."
             ::= { isisPartAreaAddrEntry 1 }

          isisPartAreaAddr OBJECT-TYPE
             SYNTAX OSINSAddress
             ACCESS read-only
             STATUS mandatory
             DESCRIPTION
                 "An area address reported in a Level 1 LSP in a partition
                 reachable by a non-virtual link."
             ::= { isisPartAreaAddrEntry 2 }


          -- The Virtual Adjacency Table

          -- The Virtual Adjacency Table contains information about all
          -- Virtual Adjacencies present on the system.

          isisVirtAdjTable OBJECT-TYPE
             SYNTAX SEQUENCE OF IsisVirtAdjEntry
             ACCESS not-accessible
             STATUS mandatory
             DESCRIPTION
                 "The table of virtual adjacencies."
             ::= { isisSystem 10 }

          isisVirtAdjEntry OBJECT-TYPE
             SYNTAX IsisVirtAdjEntry
             ACCESS not-accessible
             STATUS mandatory
             DESCRIPTION
                 "Each entry corresponds to a Virtual Adjacency."
             REFERENCE "{ISIS.moi virtualAdjacency (2)}"
             INDEX {  isisVirtAdjSysInstance,
                      isisVirtAdjIndex }
             ::= { isisVirtAdjTable 1 }

          IsisVirtAdjEntry ::=
             SEQUENCE {
                isisVirtAdjSysInstance
                   INTEGER,
                isisVirtAdjIndex
                   INTEGER,
                isisVirtAdjNET
                   OSINSAddress,
                isisVirtAdjMetric
                   PathCost
             }

          isisVirtAdjSysInstance OBJECT-TYPE
             SYNTAX INTEGER
             ACCESS read-only
             STATUS mandatory
             DESCRIPTION
                 "The unique identifier of the Integrated IS-IS instance
                 to which this row corresponds."
             ::= { isisVirtAdjEntry 1 }

          isisVirtAdjIndex OBJECT-TYPE
             SYNTAX INTEGER
             ACCESS read-only
             STATUS mandatory
             DESCRIPTION
                 "The identifier for the Virtual Adjacency. This is a
                 unique value amongst all virtual adjacencies on the same
                 circuit assigned by the implementation when the virtual
                 adjacency is created."
             ::= { isisVirtAdjEntry 2 }

          isisVirtAdjNET OBJECT-TYPE
             SYNTAX OSINSAddress
             ACCESS read-only
             STATUS mandatory
             DESCRIPTION
                 "The Network Entity Title which is the destination of the
                 virtual Adjacency being used to repair a partitioned
                 Level 1 Area"
             REFERENCE "{ISIS.aoi networkEntityTitle (88)}"
             ::= { isisVirtAdjEntry 3 }

          isisVirtAdjMetric OBJECT-TYPE
             SYNTAX PathCost
             ACCESS read-only
             STATUS mandatory
             DESCRIPTION
                 "The cost of the least cost level 2 path(s) using the
                 default metric to the destination of the virtual
                 Adjacency."
             REFERENCE "{ISIS.aoi metric (89)}"
             ::= { isisVirtAdjEntry 4 }



          -- The Circuit Group

          -- The Circuit Group is mandatory


          -- The Circuit Table

          -- Each broadcast or point-to-point interface on the system
          -- corresponds to one entry in the Circuit table. There may be
          -- many X.25 DA circuit entries in the Circuit table for an
          -- X.25 interface.

          isisCircTable OBJECT-TYPE
             SYNTAX SEQUENCE OF IsisCircEntry
             ACCESS not-accessible
             STATUS mandatory
             DESCRIPTION
                 "The table of circuits used by each instance of
                 Integrated IS-IS on this system."
             ::= { isisCirc 1 }

          isisCircEntry OBJECT-TYPE
             SYNTAX IsisCircEntry
             ACCESS not-accessible
             STATUS mandatory
             DESCRIPTION
                 "An isisCircEntry exists for each circuit used by
                 Integrated IS-IS on this system."
             INDEX {  isisCircSysInstance,
                      isisCircIndex }
             ::= { isisCircTable 1 }

          IsisCircEntry ::=
             SEQUENCE {
                isisCircSysInstance
                   INTEGER,
                isisCircIndex
                   INTEGER,
                isisCircIfIndex
                   INTEGER,
                isisCircOperState
                   OperState,
                isisCircExistState
                   ExistState,
                isisCircType
                   INTEGER,
                isisCircISISHelloTimer
                   INTEGER,
                isisCircL1DefaultMetric
                   DefaultMetric,
                isisCircL1DelayMetric
                   OtherMetric,
                isisCircL1ExpenseMetric
                   OtherMetric,
                isisCircL1ErrorMetric
                   OtherMetric,
                isisCircExtDomain
                   Boolean,
                isisCircAdjChanges
                   Counter,
                isisCircInitFails
                   Counter,
                isisCircRejAdjs
                   Counter,
                isisCircOutCtrlPDUs
                   Counter,
                isisCircInCtrlPDUs
                   Counter,
                isisCircIDFieldLenMismatches
                   Counter,
                isisCircMaxAreaAddrMismatches
                   Counter,
                isisCircL2DefaultMetric
                   DefaultMetric,
                isisCircL2DelayMetric
                   OtherMetric,
                isisCircL2ExpenseMetric
                   OtherMetric,
                isisCircL2ErrorMetric
                   OtherMetric,
                isisCircManL2Only
                   Boolean,
                isisCircL1ISPriority
                   ISPriority,
                isisCircL1CircID
                   CircuitID,
                isisCircL1DesIS
                   SystemID,
                isisCircLANL1DesISChanges
                   Counter,
                isisCircL2ISPriority
                   ISPriority,
                isisCircL2CircID
                   CircuitID,
                isisCircL2DesIS
                   SystemID,
                isisCircLANL2DesISChanges
                   Counter,
                isisCircMCAddr					-- 02new, was at 29
                   INTEGER,
                isisCircPtToPtCircID
                   CircuitID,
                isisCircStaticCallInfo
                   OBJECT IDENTIFIER,
                isisCircDACallDefMetInc
                   OtherMetric,
                isisCircDACallDelMetInc
                   OtherMetric,
                isisCircDACallErrMetInc
                   OtherMetric,
                isisCircDACallExpMetInc
                   OtherMetric,
                isisCircAuthTransPwd
                   Password,
                isisCircAuthFails
                   Counter
             }

          isisCircSysInstance OBJECT-TYPE
             SYNTAX INTEGER
             ACCESS read-write
             STATUS mandatory
             DESCRIPTION
                 "The unique identifier of the Integrated IS-IS instance
                 to which this row corresponds. This object follows the
                 index behaviour."
             ::= { isisCircEntry 1 }

          isisCircIndex OBJECT-TYPE
             SYNTAX INTEGER (1..255)
             ACCESS read-write
             STATUS mandatory
             DESCRIPTION
                 "The identifier of this circuit, unique within the
                 instance of the protocol. This object follows the index
                 behaviour."
             ::= { isisCircEntry 2 }

          isisCircIfIndex OBJECT-TYPE
             SYNTAX INTEGER
             ACCESS read-write
             STATUS mandatory
             DESCRIPTION
                 "The value of ifIndex for the interface to which this
                 circuit corresponds. This object follows the
                 replaceOnlyWhileDisabled behaviour."
             ::= { isisCircEntry 3 }

          isisCircOperState OBJECT-TYPE
             SYNTAX OperState
             ACCESS read-write
             STATUS mandatory
             DESCRIPTION
                 "The operational state of the circuit. This object
                 follows the operationalState behaviour."
             DEFVAL { off }
             ::= { isisCircEntry 4 }

          isisCircExistState OBJECT-TYPE
             SYNTAX ExistState
             ACCESS read-write
             STATUS mandatory
             DESCRIPTION
                 "The existence state of this circuit. This object follows
                 the ExistenceState behaviour."
             DEFVAL { on }
             ::= { isisCircEntry 5 }

          isisCircType OBJECT-TYPE
             SYNTAX   INTEGER {
                         broadcast(1),
                         ptToPt(2),
                         staticIn(3),
                         staticOut(4),
                         dA(5)
                      }
             ACCESS read-write
             STATUS mandatory
             DESCRIPTION
                 "The type of the circuit.  This object follows the
                 replaceOnlyWhileDisabled behaviour. The type specified
                 must be compatible with the type of the interface defined
                 by the value of isisCircIfIndex."
             REFERENCE "{ISIS.aoi type (33)}"
             ::= { isisCircEntry 6 }

          isisCircISISHelloTimer OBJECT-TYPE
             SYNTAX INTEGER (1..65535)
             ACCESS read-write
             STATUS mandatory
             DESCRIPTION
                 "The period, in seconds, between IIH PDUs. It is also
                 used as the period between ISH PDUs when polling the ES
                 configuration. This object follows the resettingTimer
                 behaviour."
             REFERENCE "{ISIS.aoi iSISHelloTimer (45)}"
             DEFVAL { 3 }
             ::= { isisCircEntry 7 }

          isisCircL1DefaultMetric OBJECT-TYPE
             SYNTAX DefaultMetric
             ACCESS read-write
             STATUS mandatory
             DESCRIPTION
                 "The default metric value of this circuit for Level 1
                 traffic."
             REFERENCE "{ISIS.aoi l1DefaultMetric (35)}"
             DEFVAL { 20 }
             ::= { isisCircEntry 8 }

          isisCircL1DelayMetric OBJECT-TYPE
             SYNTAX OtherMetric
             ACCESS read-write
             STATUS mandatory
             DESCRIPTION
                 "The delay metric value of this circuit for Level 1
                 traffic. The value of zero is reserved to indicate that
                 this metric is not supported."
             REFERENCE "{ISIS.aoi l1DelayMetric (36)}"
             DEFVAL { 0 }
             ::= { isisCircEntry 9 }

          isisCircL1ExpenseMetric OBJECT-TYPE
             SYNTAX OtherMetric
             ACCESS read-write
             STATUS mandatory
             DESCRIPTION
                 "The expense metric value of this circuit for Level 1
                 traffic. The value of zero is reserved to indicate that
                 this metric is not supported."
             REFERENCE "{ISIS.aoi l1ExpenseMetric (37)}"
             DEFVAL { 0 }
             ::= { isisCircEntry 10 }

          isisCircL1ErrorMetric OBJECT-TYPE
             SYNTAX OtherMetric
             ACCESS read-write
             STATUS mandatory
             DESCRIPTION
                 "The error metric value of this circuit for Level 1
                 traffic. The value of zero is reserved to indicate that
                 this metric is not supported."
             REFERENCE "{ISIS.aoi l1ErrorMetric (38)}"
             DEFVAL { 0 }
             ::= { isisCircEntry 11 }

          isisCircExtDomain OBJECT-TYPE
             SYNTAX Boolean
             ACCESS read-write
             STATUS mandatory
             DESCRIPTION
                 "If true, suppress normal transmission of and
                 interpretation of Intra-domain ISIS PDUs on this
                 circuit."
             REFERENCE "{ISIS.aoi externalDomain (46)}"
             ::= { isisCircEntry 12 }

          isisCircAdjChanges OBJECT-TYPE
             SYNTAX Counter
             ACCESS read-only
             STATUS mandatory
             DESCRIPTION
                 "The number of times an adjacency state change has
                 occurred on this circuit."
             REFERENCE "{ISIS.aoi changesInAdjacencyState (40)}"
             ::= { isisCircEntry 13 }

          isisCircInitFails OBJECT-TYPE
             SYNTAX Counter
             ACCESS read-only
             STATUS mandatory
             DESCRIPTION
                 "The number of times initialization of this circuit has
                 failed."
             REFERENCE "{ISIS.aoi initializationFailures (41)}"
             ::= { isisCircEntry 14 }

          isisCircRejAdjs OBJECT-TYPE
             SYNTAX Counter
             ACCESS read-only
             STATUS mandatory
             DESCRIPTION
                 "The number of times an adjacency has been rejected on
                 this circuit."
             REFERENCE "{ISIS.aoi rejectedAdjacencies (42)}"
             ::= { isisCircEntry 15 }

          isisCircOutCtrlPDUs OBJECT-TYPE
             SYNTAX Counter
             ACCESS read-only
             STATUS mandatory
             DESCRIPTION
                 "The number of IS-IS control PDUs sent on this circuit."
             REFERENCE "{ISIS.aoi iSISControlPDUsSent (43)}"
             ::= { isisCircEntry 16 }

          isisCircInCtrlPDUs OBJECT-TYPE
             SYNTAX Counter
             ACCESS read-only
             STATUS mandatory
             DESCRIPTION
                 "The number of IS-IS control PDUs received on this
                 circuit."
             REFERENCE "{ISIS.aoi controlPDUsReceived (44)}"
             ::= { isisCircEntry 17 }

          isisCircIDFieldLenMismatches OBJECT-TYPE
             SYNTAX Counter
             ACCESS read-only
             STATUS mandatory
             DESCRIPTION
                 "The number of times an IS-IS control PDU with an ID
                 field length different to that for this system has been
                 received."
             REFERENCE "{ISIS.aoi iDFieldLengthMismatches (25)}"
             ::= { isisCircEntry 18 }

          isisCircMaxAreaAddrMismatches OBJECT-TYPE
             SYNTAX Counter
             ACCESS read-only
             STATUS mandatory
             DESCRIPTION
                 "Number of times a PDU is received with a different value
                 for MaximumAreaAddresses from that of the receiving
                 system."
             REFERENCE "{ISIS.aoi MaximumAreaAddressesMismatches (118)}"
             ::= { isisCircEntry 19 }

          -- The following objects map those from the linkageISISLevel2-P
          -- package

          isisCircL2DefaultMetric OBJECT-TYPE
             SYNTAX DefaultMetric
             ACCESS read-write
             STATUS mandatory
             DESCRIPTION
                 "The default metric value of this circuit for level 2
                 traffic."
             REFERENCE "{ISIS.aoi l2DefaultMetric (68)}"
             DEFVAL { 20 }
             ::= { isisCircEntry 20 }

          isisCircL2DelayMetric OBJECT-TYPE
             SYNTAX OtherMetric
             ACCESS read-write
             STATUS mandatory
             DESCRIPTION
                 "The delay metric value of this circuit for level 2
                 traffic. The value of zero is reserved to indicate that
                 this metric is not supported."
             REFERENCE "{ISIS.aoi l2DelayMetric (69)}"
             DEFVAL { 0 }
             ::= { isisCircEntry 21 }

          isisCircL2ExpenseMetric OBJECT-TYPE
             SYNTAX OtherMetric
             ACCESS read-write
             STATUS mandatory
             DESCRIPTION
                 "The expense metric value of this circuit for level 2
                 traffic. The value of zero is reserved to indicate that
                 this metric is not supported."
             REFERENCE "{ISIS.aoi l2ExpenseMetric (70)}"
             DEFVAL { 0 }
             ::= { isisCircEntry 22 }

          isisCircL2ErrorMetric OBJECT-TYPE
             SYNTAX OtherMetric
             ACCESS read-write
             STATUS mandatory
             DESCRIPTION
                 "The error metric value of this circuit for level 2
                 traffic. The value of zero is reserved to indicate that
                 this metric is not supported."
             REFERENCE "{ISIS.aoi l2ErrorMetric (71)}"
             DEFVAL { 0 }
             ::= { isisCircEntry 23 }

          isisCircManL2Only OBJECT-TYPE
             SYNTAX Boolean
             ACCESS read-write
             STATUS mandatory
             DESCRIPTION
                 "When true, indicates that this circuit is to be used
                 only for level 2. This object follows the
                 replaceOnlyWhileDisabled behaviour."
             REFERENCE "{ISIS.aoi manualL2OnlyMode (72)}"
             DEFVAL { false }
             ::= { isisCircEntry 24 }

          -- The following objects map those from the
          -- linkageISISBroadcast-P package

          isisCircL1ISPriority OBJECT-TYPE
             SYNTAX ISPriority
             ACCESS read-write
             STATUS mandatory
             DESCRIPTION
                 "The priority for becoming LAN Level 1 Deignated
                 Intermediate System on a broadcast circuit."
             REFERENCE "{ISIS.aoi l1IntermediateSystemPriority (47)}"
             DEFVAL { 64 }
             ::= { isisCircEntry 25 }

          isisCircL1CircID OBJECT-TYPE
             SYNTAX CircuitID
             ACCESS read-only
             STATUS mandatory
             DESCRIPTION
                 "The LAN ID allocated by the LAN Level 1 Designated
                 Intermediate System. Where this system is not aware of
                 the value (because it is not participating in the Level 1
                 Designated Intermediate System election), this object has
                 the value which would be proposed for this circuit (i.e.
                 the concatenation of the local system ID and the one
                 octet local Circuit ID for this circuit."
             REFERENCE "{ISIS.aoi l1CircuitID (48)}"
             ::= { isisCircEntry 26 }

          isisCircL1DesIS OBJECT-TYPE
             SYNTAX SystemID
             ACCESS read-only
             STATUS mandatory
             DESCRIPTION
                 "The ID of the LAN Level 1 Designated Intermediate System
                 on this circuit. If, for any reason this system is not
                 partaking in the relevant Designated Intermediate System
                 election process, then the value returned is the zero
                 length OCTET STRING."
             REFERENCE "{ISIS.aoi l1DesignatedIntermediateSystem (49)}"
             ::= { isisCircEntry 27 }

          isisCircLANL1DesISChanges OBJECT-TYPE
             SYNTAX Counter
             ACCESS read-only
             STATUS mandatory
             DESCRIPTION
                 "The number of times the LAN Level 1 Designated
                 Intermediate System has changed."
               REFERENCE "{ISIS.aoi
                 lanL1DesignatedIntermediateSystemChanges (50)}"
             ::= { isisCircEntry 28 }

          -- The following objects map those from the
          -- linkageISISLevel2Broadcast-P package

          isisCircL2ISPriority OBJECT-TYPE
             SYNTAX ISPriority
             ACCESS read-write
             STATUS mandatory
             DESCRIPTION
                 "The priority for becoming LAN level 2 Designated
                 Intermediate System."
             REFERENCE "{ISIS.aoi l2IntermediateSystemPriority (73)}"
             DEFVAL { 64 }
             ::= { isisCircEntry 29 }

          isisCircL2CircID OBJECT-TYPE
             SYNTAX CircuitID
             ACCESS read-only
             STATUS mandatory
             DESCRIPTION
                 "The LAN ID allocated by the LAN Level 2 Designated
                 Intermediate System. Where this system is not aware of
                 this value (because it is not participating in the Level
                 2 Designated Intermediate System election), this object
                 has the value which would be proposed for this circuit
                 (i.e. the concatenation of the local system ID and the
                 one octet local Circuit ID for this circuit."
             REFERENCE "{ISIS.aoi l2CircuitID (74)}"
             ::= { isisCircEntry 30 }

          isisCircL2DesIS OBJECT-TYPE
             SYNTAX SystemID
             ACCESS read-only
             STATUS mandatory
             DESCRIPTION
                 "The ID of the LAN Level 2 Designated Intermediate System
                 on this circuit. If, for any reason, this system is not
                 partaking in the relevant Designated Intermediate System
                 election process, then the value returned is the zero
                 length OCTET STRING."
             REFERENCE "{ISIS.aoi l2DesignatedIntermediateSystem (75)}"
             ::= { isisCircEntry 31 }

          isisCircLANL2DesISChanges OBJECT-TYPE
             SYNTAX Counter
             ACCESS read-only
             STATUS mandatory
             DESCRIPTION
                 "The number of times the LAN Level 2 Designated
                 Intermediate System has changed."
             REFERENCE "{ISIS.aoi
                lanL2DesignatedIntermediateSystemChanges (76)}"
             ::= { isisCircEntry 32 }

          isisCircMCAddr OBJECT-TYPE			-- 02new
             SYNTAX   INTEGER {
                         group (1),
                         functional (2)
                      }
             ACCESS read-write
             STATUS mandatory
             DESCRIPTION
                 "Specifies which type of multicast address will be used
                 on this circuit for ISIS PDU sending and receiving
                 (multi-destination addresses AllL1ISs and AllL2ISs) for
                 those circuit types to which it is applicable (e.g. ISO
                 8802-5). This object follows the ReplaceOnlyWhileDisabled
                 behaviour. If this object does not apply to a row for
                 some circuit type then it has read-only access."
             DEFVAL { group }
             ::= { isisCircEntry 33 }

          -- The following objects map those from the linkageISISPtToPt-P
          -- package

          isisCircPtToPtCircID OBJECT-TYPE
             SYNTAX CircuitID
             ACCESS read-only
             STATUS mandatory
             DESCRIPTION
                 "The ID of the circuit allocated during initialization.
                 If no value has been negotiated (either because the
                 adjacency is to an End System, or because initialization
                 has not yet successfully completed), this object has the
                 value which would be proposed for this circuit (i.e. the
                 concatenation of the local system ID and the one octet
                 local Circuit ID for this circuit."
             REFERENCE "{ISIS.aoi ptPtCircuitID (51)}"
             ::= { isisCircEntry 34 }

          -- The following objects map those from the linkageISIStatic-P
          -- package

          isisCircStaticCallInfo OBJECT-TYPE
             SYNTAX OBJECT IDENTIFIER
             ACCESS read-write
             STATUS mandatory
             DESCRIPTION
                 "An OBJECT IDENTIFIER that identifies call setup
                 information (in particular the DTE address to call) for
                 use when a static circuit is enabled. This object loosely
                 maps the outgoingCallIVMO attribute of the
                 linkageISIStatic-P package. An implementation may use a
                 separate mechanism for providing call setup information."
             DEFVAL { 0 }		-- was { { 0 0 } }
             ::= { isisCircEntry 35 }

          -- The following objects map those from the
          -- linkageISISDACallEstablishmentMetricIncrement-P package

          isisCircDACallDefMetInc OBJECT-TYPE
             SYNTAX OtherMetric
             ACCESS read-write
             STATUS mandatory
             DESCRIPTION
                 "Additional value to be reported for the default metric
                 value of unestablished DA adjacencies."
             REFERENCE "{ISIS.aoi
                callEstablishmentDefaultMetricIncrement (52)}"
             DEFVAL { 0 }
             ::= { isisCircEntry 36 }

          isisCircDACallDelMetInc OBJECT-TYPE
             SYNTAX OtherMetric
             ACCESS read-write
             STATUS mandatory
             DESCRIPTION
                 "Additional value to be reported for the delay metric
                 value of unestablished DA adjacencies."
             REFERENCE "{ISIS.aoi
                callEstablishmentDelayMetricIncrement (53)}"
             DEFVAL { 0 }
             ::= { isisCircEntry 37 }

          isisCircDACallErrMetInc OBJECT-TYPE
             SYNTAX OtherMetric
             ACCESS read-write
             STATUS mandatory
             DESCRIPTION
                 "Additional value to be reported for the error metric
                 value of unestablished DA adjacencies."
             REFERENCE "{ISIS.aoi
                callEstablishmentErrorMetricIncrement (55)}"
             DEFVAL { 0 }
             ::= { isisCircEntry 38 }

          isisCircDACallExpMetInc OBJECT-TYPE
             SYNTAX OtherMetric
             ACCESS read-write
             STATUS mandatory
             DESCRIPTION
                 "Additional value to be reported for the expense metric
                 value of unestablished DA adjacencies."
             REFERENCE "{ISIS.aoi
                callEstablishmentExpenseMetricIncrement (54)}"
             DEFVAL { 0 }
             ::= { isisCircEntry 39 }

          -- The following objects map some of those from the
          -- linkageISISAuthentication-P package

          isisCircAuthTransPwd OBJECT-TYPE
             SYNTAX Password
             ACCESS read-write
             STATUS mandatory
             DESCRIPTION
                 "The value to be used as a transmit password in in IIH
                 PDUs transmitted by this Intermediate System."
             REFERENCE "{ISIS.aoi circuitTransmitPassword (115)}"
             DEFVAL { ''H }
             ::= { isisCircEntry 40 }

          isisCircAuthFails OBJECT-TYPE
             SYNTAX Counter
             ACCESS read-only
             STATUS mandatory
             DESCRIPTION
                 "The number of authentication failures on this circuit."
             REFERENCE "{ISIS.aoi authenticationFailures (117)}"
             ::= { isisCircEntry 41 }



          -- The Circuit IS Group

          -- The Circuit IS Group is present if the system supports the
          -- IS functions of the ISO 9542 protocol.


          -- The Circuit IS Table

          -- The Circuit IS Table contains objects controlling the
          -- operation of the IS functions of the ES-IS protocol
          -- (ISO 9542) on each circuit over which ISIS is run.
          -- Objects in this table map those in the linkage-ISO9542IS-P
          -- package defined in the GDMO in ISO 10733 [5].

          isisCircISTable OBJECT-TYPE
             SYNTAX SEQUENCE OF IsisCircISEntry
             ACCESS not-accessible
             STATUS mandatory
             DESCRIPTION
                 "The set of objects controlling the operation of the IS
                 functions of the ES-IS protocol (ISO 9542) on each
                 circuit over which ISIS is run."
             REFERENCE "{NLM.poi linkage-ISO9542IS-P (22)}"
             ::= { isisCirc 2 }

          isisCircISEntry OBJECT-TYPE
             SYNTAX IsisCircISEntry
             ACCESS not-accessible
             STATUS mandatory
             DESCRIPTION
                 "Each entry contains objects controlling the operation of
                 the IS functions of the ES-IS protocol (ISO 9542) on one
                 circuit."
             INDEX {  isisCircISSysInstance,			-- 02new
                      isisCircISIndex }
             ::= { isisCircISTable 1 }

          IsisCircISEntry ::=
             SEQUENCE {
                isisCircISSysInstance				-- 02new
                   INTEGER,
                isisCircISIndex
                   INTEGER,
                isisCircISExistState
                   ExistState,
                isisCircISOperState
                   OperState,
                isisCircISHoldTimerMult
                   INTEGER,
                isisCircISConfTimer
                   INTEGER,
                isisCircISSuggESConfTimer
                   INTEGER,
                isisCircISRedHoldTime
                   INTEGER,
                isisCircISMCAddr				-- 02new
                   INTEGER,
                isisCircISESReachChgs
                   Counter,
                isisCircISInv9542PDUs
                   Counter
             }

          isisCircISSysInstance OBJECT-TYPE			-- 02new
             SYNTAX INTEGER
             ACCESS read-write
             STATUS mandatory
             DESCRIPTION
                 "The unique identifier of the Integrated IS-IS instance
                 to which this row corresponds. This object follows the
                 index behaviour."
             ::= { isisCircISEntry 1 }

          isisCircISIndex OBJECT-TYPE
             SYNTAX INTEGER
             ACCESS read-write
             STATUS mandatory
             DESCRIPTION				-- 02new
                 "The unique identifier of this row. This value is the
                 same as the value of the isisCircIndex object which
                 identifies the circuit which corresponds to this row.
                 This object follows the index behaviour."
             ::= { isisCircISEntry 2 }

          isisCircISExistState OBJECT-TYPE
             SYNTAX ExistState
             ACCESS read-write
             STATUS mandatory
             DESCRIPTION				-- 02new
                 "The existence state of this row. This object follows the
                 ExistenceState behaviour. For broadcast, Point-to-Point,
                 StaticIn and StaticOut circuit types, normally there is
                 one row in this table for every corresponding row in the
                 isisCirc table. An implementation can choose to require
                 this and make this object and the isisCircISOperState
                 object read-only for those rows. In that case a row in
                 this table is automatically created when the
                 corresponding row in the isisCirc table is created and is
                 also automatically deleted when the corresponding row in
                 the isisCirc table is deleted."
             DEFVAL { on }
             ::= { isisCircISEntry 3 }

          isisCircISOperState OBJECT-TYPE
             SYNTAX OperState
             ACCESS read-write
             STATUS mandatory
             DESCRIPTION					-- 02new
                 "The operational state of the row. This object follows
                 the operationalState behaviour. For broadcast,
                 Point-to-Point, StaticIn and StaticOut circuit types,
                 normally there is one row in this table for every
                 corresponding row in the isisCirc table. An
                 implementation can choose to require this and make this
                 object and the isisCircISExistState object read-only for
                 those rows. In that case a row in this table is
                 automatically enabled when the corresponding row in the
                 isisCirc table is enabled and is also automatically
                 disabled when the corresponding row in the isisCirc table
                 is disabled."
             DEFVAL { off }
             ::= { isisCircISEntry 4 }

          isisCircISHoldTimerMult OBJECT-TYPE
             SYNTAX INTEGER (2..63)
             ACCESS read-write
             STATUS mandatory
             DESCRIPTION
                 "The factor to derive holding timer from configuration
                 timer. This value when multipled by a configuration timer
                 yields the value of the holding timer parameter issued
                 with configuration information. The semantics of this
                 parameter are such that it is permissible to add a delta
                 value to the result to compensate for possible delays and
                 imprecision of timers. The result of the calculation is
                 truncated, upon overflow, to the maximum value for the
                 parameter permitted by the protocol (65535)."
             REFERENCE "{NLM.aoi holdingTimerMutliplier (20)}"
             DEFVAL { 3 }
             ::= { isisCircISEntry 5 }

          isisCircISConfTimer OBJECT-TYPE
             SYNTAX INTEGER
             ACCESS read-write
             STATUS mandatory
             DESCRIPTION
                 "Value in seconds for the ISO 9542 IS configuration
                 timer. It is used to determine how often an IS reports
                 configuration information to ESs. This object follows the
                 resettingTimer behaviour."
             REFERENCE "{NLM.aoi iSConfigurationTimer (24)}"
             DEFVAL { 10 }
             ::= { isisCircISEntry 6 }

          isisCircISSuggESConfTimer OBJECT-TYPE
             SYNTAX INTEGER
             ACCESS read-write
             STATUS mandatory
             DESCRIPTION
                 "Value to be used for the ISO 9542 suggested ES
                 configuration timer value (in seconds), advertised in IS
                 Hellos generated by the system on this circuit. This
                 object follows the resettingTimer behaviour."
             REFERENCE "{NLM.aoi suggestedESConfigurationTimer (25)}"
             DEFVAL { 600 }
             ::= { isisCircISEntry 7 }

          isisCircISRedHoldTime OBJECT-TYPE
             SYNTAX INTEGER (1..65535)
             ACCESS read-write
             STATUS mandatory
             DESCRIPTION
                 "The holding time (in seconds) to be specified in
                 Redirect PDUs generated by the system on this circuit."
             REFERENCE "{NLM.aoi redirectHoldingTime (26)}"
             DEFVAL { 600 }
             ::= { isisCircISEntry 8 }

          isisCircISMCAddr OBJECT-TYPE				-- 02new
             SYNTAX   INTEGER {
                         group (1),
                         functional (2)
                      }
             ACCESS read-write
             STATUS mandatory
             DESCRIPTION
                 "Specifies which type of multicast address will be used
                 on this circuit for ES-IS PDU (ISO 9542) sending and
                 receiving (multi-destination addresses
                 AllIntermediateSystems and AllEndSystems) for those
                 circuit types to which it is applicable (e.g. ISO
                 8802-5). This object follows the ReplaceOnlyWhileDisabled
                 behaviour. If this object does not apply to a row for
                 some circuit type then it has read-only access."
             DEFVAL { group }
             ::= { isisCircISEntry 9 }

          isisCircISESReachChgs OBJECT-TYPE
             SYNTAX Counter
             ACCESS read-only
             STATUS mandatory
             DESCRIPTION
                 "Count of the number of changes in reachability of End
                 Systems from this circuit."
             REFERENCE "{NLM.aoi eSReachabilityChanges (27)}"
             ::= { isisCircISEntry 10 }

          isisCircISInv9542PDUs OBJECT-TYPE
             SYNTAX Counter
             ACCESS read-only
             STATUS mandatory
             DESCRIPTION
                 "Counter of invalid 9542 PDUs received. This is the
                 number of ISO 9452 PDUs received which are discarded as a
                 result of the PDU Header Error Detection or Protocol
                 Error Processing Functions specified in ISO 9542."
             REFERENCE "{NLM.aoi invalid9542PDUs (101)}"
             ::= { isisCircISEntry 11 }




          -- The Circuit Authentication Group

          -- The Circuit Authentication Group is present if the Circuit
          -- authentication procedures are implemented.


          -- The Circuit Receive Password Table

          -- Each entry contains one password to treat as valid in
          -- received IIH PDUs on the corresponding circuit.

          -- This table maps some of the objects from the
          -- linkageISISAuthentication-P package

          isisCircAuthRecPwdTable OBJECT-TYPE
             SYNTAX SEQUENCE OF IsisCircAuthRecPwdEntry
             ACCESS not-accessible
             STATUS mandatory
             DESCRIPTION
                 "The set of passwords to use for checking received IIH
                 PDUs."
             REFERENCE "{ISIS.aoi circuitReceivePasswords (116)}"
             ::= { isisCirc 3 }

          isisCircAuthRecPwdEntry OBJECT-TYPE
             SYNTAX IsisCircAuthRecPwdEntry
             ACCESS not-accessible
             STATUS mandatory
             DESCRIPTION
                 "Each entry contains one password to treat as valid in a
                 received IIH PDU on a circuit."
             INDEX {  isisCircAuthRecPwdSysInstance,
                      isisCircAuthRecPwdCircIndex,
                      isisCircAuthRecPwd }
             ::= { isisCircAuthRecPwdTable 1 }

          IsisCircAuthRecPwdEntry ::=
             SEQUENCE {
                isisCircAuthRecPwdSysInstance
                   INTEGER,
                isisCircAuthRecPwdCircIndex
                   INTEGER,
                isisCircAuthRecPwd
                   Password,
                isisCircAuthRecPwdExistState
                   ExistState
             }

          isisCircAuthRecPwdSysInstance OBJECT-TYPE
             SYNTAX INTEGER
             ACCESS read-write
             STATUS mandatory
             DESCRIPTION
                 "The unique identifier of the Integrated IS-IS instance
                 to which this row corresponds. This object follows the
                 index behaviour."
             ::= { isisCircAuthRecPwdEntry 1 }

          isisCircAuthRecPwdCircIndex OBJECT-TYPE
             SYNTAX INTEGER
             ACCESS read-write
             STATUS mandatory
             DESCRIPTION
                 "The identifier of the Circuit corresponding to this
                 password entry. This object follows the index behaviour."
             ::= { isisCircAuthRecPwdEntry 2 }

          isisCircAuthRecPwd OBJECT-TYPE
             SYNTAX Password
             ACCESS read-write
             STATUS mandatory
             DESCRIPTION
                 "A password to treat as valid in a received IIH PDU on
                 this circuit. This object follows the index behaviour."
             ::= { isisCircAuthRecPwdEntry 3 }

          isisCircAuthRecPwdExistState OBJECT-TYPE
             SYNTAX ExistState
             ACCESS read-write
             STATUS mandatory
             DESCRIPTION
                 "The existence state of the isisCircAuthRecPwdEntry. This
                 object follows the ExistenceState behaviour."
             DEFVAL { on }
             ::= { isisCircAuthRecPwdEntry 4 }




          -- The IS Adjacency Group

          -- The IS Adjacency Group is mandatory and contains information
          -- about adjacencies to routers maintained by the Integrated
          -- IS-IS protocol


          -- The IS Adjacency Table

          -- Each adjacency to an IS corresponds to one entry in this
          -- table.

          isisISAdjTable OBJECT-TYPE
             SYNTAX SEQUENCE OF IsisISAdjEntry
             ACCESS not-accessible
             STATUS mandatory
             DESCRIPTION
                 "The table of adjacencies to Intermediate Systems."
             ::= { isisISAdj 1 }

          isisISAdjEntry OBJECT-TYPE
             SYNTAX IsisISAdjEntry
             ACCESS not-accessible
             STATUS mandatory
             DESCRIPTION
                 "Each entry corresponds to one adjacency to an
                 Intermediate System on this system."
             INDEX {  isisISAdjSysInstance,
                      isisISAdjCircIndex,
                      isisISAdjIndex }
             ::= { isisISAdjTable 1 }

          IsisISAdjEntry ::=
             SEQUENCE {
                isisISAdjSysInstance
                   INTEGER,
                isisISAdjCircIndex
                   INTEGER,
                isisISAdjIndex
                   INTEGER,
                isisISAdjState
                   INTEGER,
                isisISAdjNeighSNPAAddress
                   SNPAAddress,
                isisISAdjNeighSysType
                   INTEGER,
                isisISAdjNeighSysID
                   OCTET STRING,
                isisISAdjUsage
                   INTEGER,
                isisISAdjHoldTimer
                   INTEGER,
                isisISAdjNeighPriority
                   ISPriority
             }

          isisISAdjSysInstance OBJECT-TYPE
             SYNTAX INTEGER
             ACCESS read-only
             STATUS mandatory
             DESCRIPTION
                 "The unique identifier of the Integrated IS-IS instance
                 to which this row corresponds."
             ::= { isisISAdjEntry 1 }

          isisISAdjCircIndex OBJECT-TYPE
             SYNTAX INTEGER
             ACCESS read-only
             STATUS mandatory
             DESCRIPTION
                 "The identifier of the Circuit which is the parent of the
                 IS adjacency."
             ::= { isisISAdjEntry 2 }

          isisISAdjIndex OBJECT-TYPE
             SYNTAX INTEGER
             ACCESS read-only
             STATUS mandatory
             DESCRIPTION
                 "A unique value identifying the IS adjacency from all
                 other such adjacencies on this circuit. This value is
                 assigned by the system when the adjacency is created
                 automatically."
             ::= { isisISAdjEntry 3 }

          isisISAdjState OBJECT-TYPE
             SYNTAX   INTEGER {
                         initializing (1),
                         up (2),
                         failed (3),
                         down (4)
                      }
             ACCESS read-only
             STATUS mandatory
             DESCRIPTION
                 "The state of the adjacency"
             REFERENCE "{ISIS.aoi adjacencyState (78)}"
             ::= { isisISAdjEntry 4 }

          isisISAdjNeighSNPAAddress OBJECT-TYPE
             SYNTAX SNPAAddress
             ACCESS read-only
             STATUS mandatory
             DESCRIPTION
                 "The SNPA address of the neighboring system."
             REFERENCE "{ISIS.aoi neighbourSNPAAddress (79)}"
             ::= { isisISAdjEntry 5 }

          isisISAdjNeighSysType OBJECT-TYPE
             SYNTAX   INTEGER {
                         unknown(1),
                         intermediateSystem(3),
                         l1IntermediateSystem(4),
                         l2IntermediateSystem(5)
                      }
             ACCESS read-only
             STATUS mandatory
             DESCRIPTION
                 "The type of the neighboring system."
             REFERENCE "{ISIS.aoi neighbourSystemType (80)}"
             ::= { isisISAdjEntry 6 }

          isisISAdjNeighSysID OBJECT-TYPE
             SYNTAX OCTET STRING (SIZE(0..9))
             ACCESS read-only
             STATUS mandatory
             DESCRIPTION
                 "The system ID of the neighboring Intermediate System set
                 from the source ID field of the neighbor's IIH PDUs."
             REFERENCE "{ISIS.aoi neighbourSystemIds (83)}"
             ::= { isisISAdjEntry 7 }

          isisISAdjUsage OBJECT-TYPE
             SYNTAX   INTEGER {
                         undefined(1),
                         level1(2),
                         level2(3),
                         level1and2(4)
                      }
             ACCESS read-only
             STATUS mandatory
             DESCRIPTION
                 "The usage of the adjacency. An adjacency of type level1
                 will be used for level 1 traffic only. An adjacency of
                 type level2 will be used for level 2 traffic only. An
                 adjacency of type level1and2 will be used for both level
                 1 and level 2 traffic. There may be two adjacencies (of
                 types level1 and level2) between the same pair of
                 Intermediate Systems."
             REFERENCE "{ISIS.aoi adjacencyUsage (82)}"
             ::= { isisISAdjEntry 8 }

          isisISAdjHoldTimer OBJECT-TYPE
             SYNTAX INTEGER (1..65535)
             ACCESS read-only
             STATUS mandatory
             DESCRIPTION
                 "The holding time for this adjacency updated from
                 received IIH PDUs."
             REFERENCE "{ISIS.aoi holdingTimer (85)}"
             ::= { isisISAdjEntry 9 }

          isisISAdjNeighPriority OBJECT-TYPE
             SYNTAX ISPriority
             ACCESS read-only
             STATUS mandatory
             DESCRIPTION
                 "Priority of the neighboring Intermediate System for
                 becoming the LAN Level 1 Designated Intermediate System
                 if the value of isisISAdjNeighSysType is
                 L1IntermediateSystem or LAN Level 2 Designated
                 Intermediate System if the value of
                 isisISAdjNeighSysType is L2IntermediateSystem."
             REFERENCE "{ISIS.aoi lANPriority (86)}"
             ::= { isisISAdjEntry 10 }


          -- The IS Adjacency Area Address Table

          -- The IS Adjacency Area Address Table contains the set of
          -- Area Addresses of neighboring
          -- Intermediate Systems as reported in IIH PDUs.

          isisISAdjAreaAddrTable OBJECT-TYPE
             SYNTAX SEQUENCE OF IsisISAdjAreaAddrEntry
             ACCESS not-accessible
             STATUS mandatory
             DESCRIPTION
                 "This table contains the set of Area Addresses of
                 neighboring Intermediate Systems as reported in received
                 IIH PDUs."
             REFERENCE "{ISIS.aoi areaAddressesOfNeighbour (84)}"
             ::= { isisISAdj 2 }

          isisISAdjAreaAddrEntry OBJECT-TYPE
             SYNTAX IsisISAdjAreaAddrEntry
             ACCESS not-accessible
             STATUS mandatory
             DESCRIPTION
                 "Each entry contains one Area Address reported by a
                 neighboring Intermediate System in its IIH PDUs."
             INDEX {  isisISAdjAreaAddrSysInstance,
                      isisISAdjAreaAddrCircIndex,
                      isisISAdjAreaAddrAdjIndex,
                      isisISAdjAreaAddress }
             ::= { isisISAdjAreaAddrTable 1 }

          IsisISAdjAreaAddrEntry ::=
             SEQUENCE {
                isisISAdjAreaAddrSysInstance
                   INTEGER,
                isisISAdjAreaAddrCircIndex
                   INTEGER,
                isisISAdjAreaAddrAdjIndex
                   INTEGER,
                isisISAdjAreaAddress
                   OSINSAddress
             }

          isisISAdjAreaAddrSysInstance OBJECT-TYPE
             SYNTAX INTEGER
             ACCESS read-only
             STATUS mandatory
             DESCRIPTION
                 "The unique identifier of the Integrated IS-IS instance
                 to which this row corresponds."
             ::= { isisISAdjAreaAddrEntry 1 }

          isisISAdjAreaAddrCircIndex OBJECT-TYPE
             SYNTAX INTEGER
             ACCESS read-only
             STATUS mandatory
             DESCRIPTION
                 "The identifier of the Circuit which is the parent of the
                 IS adjacency to which this Area Address entry
                 corresponds."
             ::= { isisISAdjAreaAddrEntry 2 }

          isisISAdjAreaAddrAdjIndex OBJECT-TYPE
             SYNTAX INTEGER
             ACCESS read-only
             STATUS mandatory
             DESCRIPTION
                 "The identifier of the IS adjacency to which this entry
                 belongs."
             ::= { isisISAdjAreaAddrEntry 3 }

          isisISAdjAreaAddress OBJECT-TYPE
             SYNTAX OSINSAddress
             ACCESS read-only
             STATUS mandatory
             DESCRIPTION
                 "One Area Address as reported in IIH PDUs received from
                 the neighbor."
             ::= { isisISAdjAreaAddrEntry 4 }



          -- The IS Adjacency IP Group

          -- The IS Adjacency IP Group is present if the system supports
          -- IP Integrated IS-IS


          -- The IS Adjacency IP Address Table

          -- The IS Adjacency IP Address Table contains the
          -- set of IP Addresses of neighboring Intermediate Systems
          -- as reported in received IIH PDUs.

          isisISAdjIPAddrTable OBJECT-TYPE
             SYNTAX SEQUENCE OF IsisISAdjIPAddrEntry
             ACCESS not-accessible
             STATUS mandatory
             DESCRIPTION
                 "This table contains the set of IP Addresses of
                 neighboring Intermediate Systems as reported in received
                 IIH PDUs."
             ::= { isisISAdj 3 }

          isisISAdjIPAddrEntry OBJECT-TYPE
             SYNTAX IsisISAdjIPAddrEntry
             ACCESS not-accessible
             STATUS mandatory
             DESCRIPTION
                 "Each entry contains one IP Address reported by a
                 neighboring Intermediate System in its IIH PDUs."
             INDEX {  isisISAdjIPAddrSysInstance,
                      isisISAdjIPAddrCircIndex,
                      isisISAdjIPAddrAdjIndex,
                      isisISAdjIPAddress }
             ::= { isisISAdjIPAddrTable 1 }

          IsisISAdjIPAddrEntry ::=
             SEQUENCE {
                isisISAdjIPAddrSysInstance
                   INTEGER,
                isisISAdjIPAddrCircIndex
                   INTEGER,
                isisISAdjIPAddrAdjIndex
                   INTEGER,
                isisISAdjIPAddress
                   IpAddress
             }

          isisISAdjIPAddrSysInstance OBJECT-TYPE
             SYNTAX INTEGER
             ACCESS read-only
             STATUS mandatory
             DESCRIPTION
                 "The unique identifier of the Integrated IS-IS instance
                 to which this row corresponds."
             ::= { isisISAdjIPAddrEntry 1 }

          isisISAdjIPAddrCircIndex OBJECT-TYPE
             SYNTAX INTEGER
             ACCESS read-only
             STATUS mandatory
             DESCRIPTION
                 "The identifier of the Circuit which is the parent of the
                 IS adjacency to which this IP Address entry corresponds."
             ::= { isisISAdjIPAddrEntry 2 }

          isisISAdjIPAddrAdjIndex OBJECT-TYPE
             SYNTAX INTEGER
             ACCESS read-only
             STATUS mandatory
             DESCRIPTION
                 "The identifier of the IS adjacency to which this entry
                 belongs."
             ::= { isisISAdjIPAddrEntry 3 }

          isisISAdjIPAddress OBJECT-TYPE
             SYNTAX IpAddress
             ACCESS read-only
             STATUS mandatory
             DESCRIPTION
                 "One IP Address as reported in IIH PDUs received from the
                 neighbor."
             ::= { isisISAdjIPAddrEntry 4 }





          -- The IS Adjacency Integrated Group

          -- The IS Adjacency Integrated Group is present if the system
          -- supports Integrated ISIS.


          -- The IS Adjacency Protocol Supported Table

          -- The IS Adjacency Protocol Supported Table contains the set of
          -- protocols supported by neighboring
          -- Intermediate Systems as reported in received IIH PDUs.

          isisISAdjProtSuppTable OBJECT-TYPE
             SYNTAX SEQUENCE OF IsisISAdjProtSuppEntry
             ACCESS not-accessible
             STATUS mandatory
             DESCRIPTION
                 "This table contains the set of protocols supported by
                 neighboring Intermediate Systems as reported in received
                 IIH PDUs."
             ::= { isisISAdj 4 }

          isisISAdjProtSuppEntry OBJECT-TYPE
             SYNTAX IsisISAdjProtSuppEntry
             ACCESS not-accessible
             STATUS mandatory
             DESCRIPTION
                 "Each entry contains one protocol supported by a
                 neighboring Intermediate System as reported in its IIH
                 PDUs."
             INDEX {  isisISAdjProtSuppSysInstance,
                      isisISAdjProtSuppCircIndex,
                      isisISAdjProtSuppAdjIndex,
                      isisISAdjProtSuppProtocol }
             ::= { isisISAdjProtSuppTable 1 }

          IsisISAdjProtSuppEntry ::=
             SEQUENCE {
                isisISAdjProtSuppSysInstance
                   INTEGER,
                isisISAdjProtSuppCircIndex
                   INTEGER,
                isisISAdjProtSuppAdjIndex
                   INTEGER,
                isisISAdjProtSuppProtocol
                   SupportedProtocol
             }

          isisISAdjProtSuppSysInstance OBJECT-TYPE
             SYNTAX INTEGER
             ACCESS read-only
             STATUS mandatory
             DESCRIPTION
                 "The unique identifier of the Integrated IS-IS instance
                 to which this row corresponds."
             ::= { isisISAdjProtSuppEntry 1 }

          isisISAdjProtSuppCircIndex OBJECT-TYPE
             SYNTAX INTEGER
             ACCESS read-only
             STATUS mandatory
             DESCRIPTION
                 "The identifier of the Circuit which is the parent of the
                 IS adjacency to which this supported protocol entry
                 corresponds."
             ::= { isisISAdjProtSuppEntry 2 }

          isisISAdjProtSuppAdjIndex OBJECT-TYPE
             SYNTAX INTEGER
             ACCESS read-only
             STATUS mandatory
             DESCRIPTION
                 "The identifier the IS adjacency to which this entry
                 corresponds."
             ::= { isisISAdjProtSuppEntry 3 }

          isisISAdjProtSuppProtocol OBJECT-TYPE
             SYNTAX SupportedProtocol
             ACCESS read-only
             STATUS mandatory
             DESCRIPTION
                 "One supported protocol as reported in IIH PDUs received
                 from the neighbor."
             ::= { isisISAdjProtSuppEntry 4 }




          -- The ES Adjacency Group

          -- The ES Adjacency Group is present if the system supports
          -- reception of ES Hellos


          -- The ES Adjacency Table

          -- The ES Adjacency Table contains one entry for each
          -- End System ID of each neighboring End System
          -- as reported in ESH PDUs or as configured manually.

          isisESAdjTable OBJECT-TYPE
             SYNTAX SEQUENCE OF IsisESAdjEntry
             ACCESS not-accessible
             STATUS mandatory
             DESCRIPTION
                 "The table of End System IDs of neighboring End Systems
                 as reported in their ESH PDUs or as configured manually"
             ::= { isisESAdj 1 }

          isisESAdjEntry OBJECT-TYPE
             SYNTAX IsisESAdjEntry
             ACCESS not-accessible
             STATUS mandatory
             DESCRIPTION
                 "Each entry contains one End System ID of a neighboring
                 End System as reported in an ESH PDU or as configured
                 manually."
             INDEX {  isisESAdjSysInstance,
                      isisESAdjCircIndex,
                      isisESAdjType,				-- 02new
                      isisESAdjAdjIndex,
                      isisESAdjESID }
             ::= { isisESAdjTable 1 }

          IsisESAdjEntry ::=
             SEQUENCE {
                isisESAdjSysInstance
                   INTEGER,
                isisESAdjCircIndex
                   INTEGER,
                isisESAdjAdjIndex
                   INTEGER,
                isisESAdjType
                   INTEGER,
                isisESAdjState
                   INTEGER,
                isisESAdjNeighSNPAAddress
                   SNPAAddress,
                isisESAdjExistState
                   ExistState,
                isisESAdjESID
                   SystemID
             }

          isisESAdjSysInstance OBJECT-TYPE
             SYNTAX INTEGER
             ACCESS read-write
             STATUS mandatory
             DESCRIPTION
                 "The identifier of the Integrated IS-IS instance to which
                 this row corresponds. This object follows the index and
                 manualOrAutomatic behaviours."
             ::= { isisESAdjEntry 1 }

          isisESAdjCircIndex OBJECT-TYPE
             SYNTAX INTEGER
             ACCESS read-write
             STATUS mandatory
             DESCRIPTION
                 "The identifier of the Circuit which is the parent of the
                 ES adjacency to which this End System ID entry
                 corresponds. This object follows the index and
                 manualOrAutomatic behaviours."
             ::= { isisESAdjEntry 2 }

          isisESAdjAdjIndex OBJECT-TYPE
             SYNTAX INTEGER
             ACCESS read-write
             STATUS mandatory
             DESCRIPTION
                 "The identifier of the ES adjacency to which this entry
                 belongs. This object follows the index and
                 manualOrAutomatic behaviours."
             ::= { isisESAdjEntry 3 }

          isisESAdjType OBJECT-TYPE
             SYNTAX   INTEGER  {
                         auto (1),
                         manual (2)
                      }
             ACCESS read-only
             STATUS mandatory
             DESCRIPTION
                 "The indication of whether this adjacency was created
                 manually by management action or automatically by the
                 implementation."
             ::= { isisESAdjEntry 4 }

          isisESAdjState OBJECT-TYPE
             SYNTAX   INTEGER {
                         initializing (1),
                         up (2),
                         failed (3),
                         down (4)
                      }
             ACCESS read-only
             STATUS mandatory
             DESCRIPTION
                 "The state of the adjacency. Adjacencies created manually
                 always have this value set to up."
             REFERENCE "{ISIS.aoi adjacencyState (78)}"
             DEFVAL { up }
             ::= { isisESAdjEntry 5 }

          isisESAdjNeighSNPAAddress OBJECT-TYPE
             SYNTAX SNPAAddress
             ACCESS read-write
             STATUS mandatory
             DESCRIPTION
                 "The SNPA address of the neighboring system. This object
                 follows the manualOrAutomatic behaviour."
             REFERENCE "{ISIS.aoi neighbourSNPAAddress (79)}"
             ::= { isisESAdjEntry 6 }

          isisESAdjExistState OBJECT-TYPE
             SYNTAX ExistState
             ACCESS read-write
             STATUS mandatory
             DESCRIPTION					-- 02new
                 "The existence state of this ES Adjacency. This object
                 follows the ExistenceState and manualOrAutomatic
                 behaviours."
             DEFVAL { on }
             ::= { isisESAdjEntry 7 }

          isisESAdjESID OBJECT-TYPE
             SYNTAX SystemID
             ACCESS read-write
             STATUS mandatory
             DESCRIPTION
                 "An End System ID of a neighboring End System. This
                 object follows the index and manualOrAutomatic
                 behaviour."
             ::= { isisESAdjEntry 8 }




          -- The Reachable Address Group

          -- The Reachable Address Group is optional.


          -- The Reachable Address Table

          -- Each entry records information about a reachable address
          -- (NSAP or address prefix) manually configured on the system
          -- or learned through another protocol.

          isisRATable OBJECT-TYPE
             SYNTAX SEQUENCE OF IsisRAEntry
             ACCESS not-accessible
             STATUS mandatory
             DESCRIPTION
                 "The table of Reachable Addresses to NSAPs or Address
                 Prefixes."
             ::= { isisReachAddr 1 }

          isisRAEntry OBJECT-TYPE
             SYNTAX IsisRAEntry
             ACCESS not-accessible
             STATUS mandatory
             DESCRIPTION
                 "Each entry defines a Reachable Address to a NSAP or
                 Address Prefix."
             INDEX {  isisRASysInstance,
                      isisRACircIndex,
                      isisRAType,
                      isisRAIndex }
             ::= { isisRATable 1 }

          IsisRAEntry ::=
             SEQUENCE {
                isisRASysInstance
                   INTEGER,
                isisRACircIndex
                   INTEGER,
                isisRAIndex
                   INTEGER,
                isisRAExistState
                   ExistState,
                isisRAOperState
                   OperState,
                isisRAAddrPrefix
                   NSAPPrefix,
                isisRAType
                   INTEGER,
                isisRAMapType
                   INTEGER,
                isisRADefMetric
                   DefaultMetric,
                isisRADelMetric
                   OtherMetric,
                isisRAExpMetric
                   OtherMetric,
                isisRAErrMetric
                   OtherMetric,
                isisRADefMetricType
                   MetricType,
                isisRADelMetricType
                   MetricType,
                isisRAExpMetricType
                   MetricType,
                isisRAErrMetricType
                   MetricType,
                isisRASNPAAddress
                   SNPAAddress,
                isisRASNPAMask
                   SNPAPrefix,
                isisRASNPAPrefix
                   SNPAPrefix
             }

          isisRASysInstance OBJECT-TYPE
             SYNTAX INTEGER
             ACCESS read-write
             STATUS mandatory
             DESCRIPTION
                 "The identifier of the Integrated IS-IS instance to which
                 this row corresponds. This object follows the index and
                 manualOrAutomatic behaviours."
             ::= { isisRAEntry 1 }

          isisRACircIndex OBJECT-TYPE
             SYNTAX INTEGER
             ACCESS read-write
             STATUS mandatory
             DESCRIPTION
                 "The identifier of the Circuit over which this
                 destination is reachable. This object follows the index
                 and manualOrAutomatic behaviours."
             ::= { isisRAEntry 2 }

          isisRAIndex OBJECT-TYPE
             SYNTAX INTEGER
             ACCESS read-write
             STATUS mandatory
             DESCRIPTION
                 "The identifier for this isisRAEntry. This value must be
                 unique amongst all Reachable Addresses on the same parent
                 Circuit. This object follows the index and
                 manualOrAutomatic behaviours."
             ::= { isisRAEntry 3 }

          isisRAExistState OBJECT-TYPE
             SYNTAX ExistState
             ACCESS read-write
             STATUS mandatory
             DESCRIPTION
                 "The existence state of this Reachable Address. This
                 object follows the ExistenceState and manualOrAutomatic
                 behaviours."
             DEFVAL { on }
             ::= { isisRAEntry 4 }

          isisRAOperState OBJECT-TYPE
             SYNTAX OperState
             ACCESS read-write
             STATUS mandatory
             DESCRIPTION
                 "The operational state of the Reachable Address. This
                 object follows the operationalState and manualOrAutomatic
                 behaviours."
             DEFVAL { off }
             ::= { isisRAEntry 5 }

          isisRAAddrPrefix OBJECT-TYPE
             SYNTAX NSAPPrefix
             ACCESS read-write
             STATUS mandatory
             DESCRIPTION
                 "The destination of this Reachable Address. This is an
                 Address Prefix. This object follows the
                 replaceOnlyWhileDisabled and manualOrAutomatic
                 behaviours."
             REFERENCE "{ISIS.aoi addressPrefix (98)}"
             ::= { isisRAEntry 6 }

          isisRAType OBJECT-TYPE
             SYNTAX   INTEGER
                         {
                            manual (1),
                            automatic (2)
                         }
             ACCESS read-only
             STATUS mandatory
             DESCRIPTION
                 "The type of this Reachable Address. Those of type manual
                 are created by the network manager. Those of type
                 automatic are created through propagation of routing
                 information from another routing protocol."
             ::= { isisRAEntry 7 }

          isisRAMapType OBJECT-TYPE
             SYNTAX   INTEGER {
                         none (1),
                         explicit (2),
                         extractIDI (3),
                         extractDSP (4)
                      }
             ACCESS read-write
             STATUS mandatory
             DESCRIPTION
                 "The type of mapping to be employed to ascertain the SNPA
                 Address which should be used in forwarding PDUs for this
                 Reachable Address prefix. This object follows the
                 manualOrAutomatic behaviour. The following values of
                 mapping type are defined:
                    none: The mapping is null because the neighbor SNPA is
                    implicit by nature of the subnetwork (e.g. a
                    point-to-point linkage).

                    explicit: The subnetwork address in the object  -- 02new
                    isisRASNPAAddress is to be used.

                    extractIDI: The SNPA is embedded in the IDI of the
                    destination NSAP Address. The mapping algorithm
                    extracts the SNPA to be used according to the format
                    and encoding rules of ISO8473/Add2. This SNPA
                    extraction algorithm can be used in conjunction with
                    Reachable Address prefixes from the X.121, F.69, E.163
                    and E.164 addressing subdomains.

                    extractDSP: All, or a suffix, of the SNPA is embedded
                    in the DSP of the destination address. This SNPA
                    extraction algorithm extracts the embedded subnetwork
                    addressing information by performing a logical AND of
                    the isisRASNPAMask object value with the destination
                    address. The part of the SNPA extracted from the
                    destination NSAP is appended to the isisRASNPAPrefix
                    object value to form the next hop subnetwork
                    addressing information."
             REFERENCE "{ISO10589-ISIS.aoi mappingType (107)}"
             ::= { isisRAEntry 8 }

          isisRADefMetric OBJECT-TYPE
             SYNTAX DefaultMetric
             ACCESS read-write
             STATUS mandatory
             DESCRIPTION
                 "The default metric value for reaching the specified
                 prefix over this circuit. This object follows the
                 manualOrAutomatic behaviour."
             REFERENCE "{ISIS.aoi defaultMetric (99)}"
             DEFVAL { 20 }
             ::= { isisRAEntry 9 }

          isisRADelMetric OBJECT-TYPE
             SYNTAX OtherMetric
             ACCESS read-write
             STATUS mandatory
             DESCRIPTION
                 "The delay metric for reaching the specified prefix over
                 this circuit. This object follows the manualOrAutomatic
                 behaviour. The value zero is reserved to indicate that
                 this metric is not supported."
             REFERENCE "{ISIS.aoi delayMetric (100)}"
             DEFVAL { 0 }
             ::= { isisRAEntry 10 }

          isisRAExpMetric OBJECT-TYPE
             SYNTAX OtherMetric
             ACCESS read-write
             STATUS mandatory
             DESCRIPTION
                 "The expense metric for reaching the specified prefix
                 over this circuit. This object follows the
                 manualOrAutomatic behaviour. The value zero is reserved
                 to indicate that this metric is not supported."
             REFERENCE "{ISIS.aoi expenseMetric (101)}"
             DEFVAL { 0 }
             ::= { isisRAEntry 11 }

          isisRAErrMetric OBJECT-TYPE
             SYNTAX OtherMetric
             ACCESS read-write
             STATUS mandatory
             DESCRIPTION
                 "The error metric for reaching the specified prefix over
                 this circuit. This object follows the manualOrAutomatic
                 behaviour. The value zero is reserved to indicate  that
                 this metric is not supported."
             REFERENCE "{ISIS.aoi errorMetric (102)}"
             DEFVAL { 0 }
             ::= { isisRAEntry 12 }

          isisRADefMetricType OBJECT-TYPE
             SYNTAX MetricType
             ACCESS read-write
             STATUS mandatory
             DESCRIPTION
                 "Indicates whether the default metric is internal or
                 external. This object follows the manualOrAutomatic
                 behaviour."
             REFERENCE "{ISIS.aoi defaultMetricType (103)}"
             DEFVAL { internal }
             ::= { isisRAEntry 13 }

          isisRADelMetricType OBJECT-TYPE
             SYNTAX MetricType
             ACCESS read-write
             STATUS mandatory
             DESCRIPTION
                 "Indicates whether the delay metric is internal or
                 external. This object follows the manualOrAutomatic
                 behaviour."
             REFERENCE "{ISO10589-ISIS.aoi delayMetricType (104)}"
             DEFVAL { internal }
             ::= { isisRAEntry 14 }

          isisRAExpMetricType OBJECT-TYPE
             SYNTAX MetricType
             ACCESS read-write
             STATUS mandatory
             DESCRIPTION
                 "Indicates whether the expense metric is internal or
                 external. This object follows the manualOrAutomatic
                 behaviour."
             REFERENCE "{ISIS.aoi expenseMetricType (105)}"
             DEFVAL { internal }
             ::= { isisRAEntry 15 }

          isisRAErrMetricType OBJECT-TYPE
             SYNTAX MetricType
             ACCESS read-write
             STATUS mandatory
             DESCRIPTION
                 "Indicates whether the error metric is internal or
                 external. This object follows the manualOrAutomatic
                 behaviour."
             REFERENCE "{ISIS.aoi errorMetricType (106)}"
             DEFVAL { internal }
             ::= { isisRAEntry 16 }

          isisRASNPAAddress OBJECT-TYPE
             SYNTAX SNPAAddress
             ACCESS read-write
             STATUS mandatory
             DESCRIPTION
                 "The SNPA Address to which a PDU may be forwarded in
                 order to reach a destination which matches the address
                 prefix of the Reachable Address. This object follows the
                 manualOrAutomatic behaviour."
             REFERENCE "{ISIS.aoi sNPAAddresses (109)}"
          -- note only one address may be specified per entry in this
          -- table						 02new
             DEFVAL { ''H }
             ::= { isisRAEntry 17 }

          isisRASNPAMask OBJECT-TYPE
             SYNTAX SNPAPrefix
             ACCESS read-write
             STATUS mandatory
             DESCRIPTION
                 "A bit mask with 1 bits indicating the positions in the
                 effective destination address from which embedded SNPA
                 information is to be extracted. For the extraction the
                 first octet of the isisRASNPAMask object value is aligned
                 with the first octet (AFI) of the NSAP Address. If the
                 isisRASNPAMask object value and NSAP Address are of
                 different lengths, the shorter of the two is logically
                 padded with zeros before performing the extraction. This
                 object follows the manualOrAutomatic behaviour."
             REFERENCE "{ISIS.aoi sNPAMask (122)}"
             DEFVAL { ''H }
             ::= { isisRAEntry 18 }

          isisRASNPAPrefix OBJECT-TYPE
             SYNTAX SNPAPrefix
             ACCESS read-write
             STATUS mandatory
             DESCRIPTION
                 "A fixed SNPA prefix for use when the isisRAMapType is
                 extractDSP. The SNPA Address to use is formed by
                 concatenating the fixed SNPA prefix with a variable SNPA
                 part that is extracted from the effective destination
                 address. For Reachable Address prefixes in which the
                 entire SNPA is embedded in the DSP the SNPA Prefix shall
                 be null. This object follows the manualOrAutomatic
                 behaviour."
             REFERENCE "{ISIS.aoi sNPAPrefix (123)}"
             DEFVAL { ''H }
             ::= { isisRAEntry 19 }




          -- The IP Reachable Address Group

          -- The IP Reachable Address Group is optional.


          -- The IP Reachable Address Table

          -- Each entry records information about one IP reachable
          -- address manually configured on this system or learned from
          -- another protocol.

          isisIPRATable OBJECT-TYPE
             SYNTAX SEQUENCE OF IsisIPRAEntry
             ACCESS not-accessible
             STATUS mandatory
             DESCRIPTION
                 "The table of IP Reachable Addresses to networks,
                 subnetworks or hosts either manually configured or
                 learned from another protocol."
             ::= { isisIPReachAddr 1 }

          isisIPRAEntry OBJECT-TYPE
             SYNTAX IsisIPRAEntry
             ACCESS not-accessible
             STATUS mandatory
             DESCRIPTION
                 "Each entry defines an IP Reachable Address to a network,
                 subnetwork or host."
             INDEX {  isisIPRASysInstance,
                      isisIPRACircIndex,
                      isisIPRAType,				-- 02new
                      isisIPRAIndex }
             ::= { isisIPRATable 1 }

          IsisIPRAEntry ::=
             SEQUENCE {
                isisIPRASysInstance
                   INTEGER,
                isisIPRACircIndex
                   INTEGER,
                isisIPRAIndex
                   INTEGER,
                isisIPRAType					-- 02new
                   INTEGER,
                isisIPRADest
                   IpAddress,
                isisIPRAMask
                   IpAddress,
                isisIPRAExistState
                   ExistState,
                isisIPRAOperState
                   OperState,
                isisIPRADefMetric
                   DefaultMetric,
                isisIPRADelMetric
                   OtherMetric,
                isisIPRAExpMetric
                   OtherMetric,
                isisIPRAErrMetric
                   OtherMetric,
                isisIPRADefMetricType
                   MetricType,
                isisIPRADelMetricType
                   MetricType,
                isisIPRAExpMetricType
                   MetricType,
                isisIPRAErrMetricType
                   MetricType,
                isisIPRASNPAAddress
                   SNPAAddress
             }

          isisIPRASysInstance OBJECT-TYPE
             SYNTAX INTEGER
             ACCESS read-write
             STATUS mandatory
             DESCRIPTION
                 "The identifier of the Integrated IS-IS instance to which
                 this row corresponds. This object follows the index and
                 manualOrAutomatic behaviours."
             ::= { isisIPRAEntry 1 }

          isisIPRACircIndex OBJECT-TYPE
             SYNTAX INTEGER
             ACCESS read-write
             STATUS mandatory
             DESCRIPTION
                 "The identifier of the Circuit over which this IP
                 destination is reachable. This object follows the index
                 and manualOrAutomatic behaviours."
             ::= { isisIPRAEntry 2 }

          isisIPRAIndex OBJECT-TYPE
             SYNTAX INTEGER
             ACCESS read-write
             STATUS mandatory
             DESCRIPTION
                 "The identifier for this isisIPRAEntry. This value must
                 be unique amongst all IP Reachable Addresses on the same
                 parent Circuit. This object follows the index and
                 manualOrAutomatic behaviours."
             ::= { isisIPRAEntry 3 }

          isisIPRAType OBJECT-TYPE			-- 02new
             SYNTAX   INTEGER
                         {
                            manual (1),
                            automatic (2)
                         }
             ACCESS read-only
             STATUS mandatory
             DESCRIPTION
                 "The type of this IP Reachable Address. Those of type
                 manual are created by the network manager. Those of type
                 automatic are created through propagation of routing
                 information from another routing protocol."
             ::= { isisIPRAEntry 4 }

          isisIPRADest OBJECT-TYPE
             SYNTAX IpAddress
             ACCESS read-write
             STATUS mandatory
             DESCRIPTION
                 "The destination of this IP Reachable Address. This is
                 either a network address, subnetwork address or host
                 address. This object follows the manualOrAutomatic
                 behaviour."
             ::= { isisIPRAEntry 5 }

          isisIPRAMask OBJECT-TYPE
             SYNTAX IpAddress
             ACCESS read-write
             STATUS mandatory
             DESCRIPTION
                 "The network mask for the IP Address in the isisIPRADest
                 object. This object follows the manualOrAutomatic
                 behaviour."
             ::= { isisIPRAEntry 6 }

          isisIPRAExistState OBJECT-TYPE
             SYNTAX ExistState
             ACCESS read-write
             STATUS mandatory
             DESCRIPTION
                 "The state of this IP Reachable Address. This object
                 follows the ExistenceState and manualOrAutomatic
                 behaviours."
             DEFVAL { on }
             ::= { isisIPRAEntry 7 }

          isisIPRAOperState OBJECT-TYPE
             SYNTAX OperState
             ACCESS read-write
             STATUS mandatory
             DESCRIPTION
                 "The operational state of the IP Reachable Address. This
                 object follows the operationalState and manualOrAutomatic
                 behaviours."
             DEFVAL { off }
             ::= { isisIPRAEntry 8 }

          isisIPRADefMetric OBJECT-TYPE
             SYNTAX DefaultMetric
             ACCESS read-write
             STATUS mandatory
             DESCRIPTION
                 "The default metric value for reaching the specified
                 destination over this circuit. This object follows the
                 manualOrAutomatic behaviour."
             DEFVAL { 20 }
             ::= { isisIPRAEntry 9 }

          isisIPRADelMetric OBJECT-TYPE
             SYNTAX OtherMetric
             ACCESS read-write
             STATUS mandatory
             DESCRIPTION
                 "The delay metric value for reaching the specified
                 destination over this circuit. The value zero is reserved
                 to mean the metric is not supported. This object follows
                 the manualOrAutomatic behaviour."
             DEFVAL { 0 }
             ::= { isisIPRAEntry 10 }

          isisIPRAExpMetric OBJECT-TYPE
             SYNTAX OtherMetric
             ACCESS read-write
             STATUS mandatory
             DESCRIPTION
                 "The expense metric value for reaching the specified
                 destination over this circuit. The value zero is reserved
                 to mean the metric is not supported. This object follows
                 the manualOrAutomatic behaviour."
             DEFVAL { 0 }
             ::= { isisIPRAEntry 11 }

          isisIPRAErrMetric OBJECT-TYPE
             SYNTAX OtherMetric
             ACCESS read-write
             STATUS mandatory
             DESCRIPTION
                 "The error metric value for reaching the specified
                 destination over this circuit. The value zero is reserved
                 to mean the metric is not supported. This object follows
                 the manualOrAutomatic behaviour."
             DEFVAL { 0 }
             ::= { isisIPRAEntry 12 }

          isisIPRADefMetricType OBJECT-TYPE
             SYNTAX MetricType
             ACCESS read-write
             STATUS mandatory
             DESCRIPTION
                 "Indicates whether the default metric is internal or
                 external. This object follows the manualOrAutomatic
                 behaviour."
             DEFVAL { internal }
             ::= { isisIPRAEntry 13 }

          isisIPRADelMetricType OBJECT-TYPE
             SYNTAX MetricType
             ACCESS read-write
             STATUS mandatory
             DESCRIPTION
                 "Indicates whether the delay metric is internal or
                 external. This object follows the manualOrAutomatic
                 behaviour."
             DEFVAL { internal }
             ::= { isisIPRAEntry 14 }

          isisIPRAExpMetricType OBJECT-TYPE
             SYNTAX MetricType
             ACCESS read-write
             STATUS mandatory
             DESCRIPTION
                 "Indicates whether the expense metric is internal or
                 external. This object follows the manualOrAutomatic
                 behaviour."
             DEFVAL { internal }
             ::= { isisIPRAEntry 15 }

          isisIPRAErrMetricType OBJECT-TYPE
             SYNTAX MetricType
             ACCESS read-write
             STATUS mandatory
             DESCRIPTION
                 "Indicates whether the error metric is internal or
                 external. This object follows the manualOrAutomatic
                 behaviour."
             DEFVAL { internal }
             ::= { isisIPRAEntry 16 }

          isisIPRASNPAAddress OBJECT-TYPE
             SYNTAX SNPAAddress
             ACCESS read-write
             STATUS mandatory
             DESCRIPTION
                 "The SNPA Address to which a PDU may be forwarded in
                 order to reach a destination which matches this IP
                 Reachable Address. This object follows the
                 manualOrAutomatic behaviour."
             DEFVAL { ''H }
             ::= { isisIPRAEntry 17 }




          -- The Level 1 CLNP Destination Group

          -- The Level 1 CLNP Destination Group is present if the system
          -- supports Level 1 and forwards ISO 8473 packets.


          -- The Level 1 CLNP Destination Table

          -- The Level 1 CLNP Destination Table records information about
          -- each end system ID destination known to the Intermediate
          -- System in the system's level 1 forwarding database.

          isisL1CLNPDestTable OBJECT-TYPE
             SYNTAX SEQUENCE OF IsisL1CLNPDestEntry
             ACCESS not-accessible
             STATUS mandatory
             DESCRIPTION
                 "The Level 1 CLNP Destination Table records information
                 about each end system ID destination known to the
                 Intermediate System."
             ::= { isisCLNPDest 1 }

          isisL1CLNPDestEntry OBJECT-TYPE
             SYNTAX IsisL1CLNPDestEntry
             ACCESS not-accessible
             STATUS mandatory
             DESCRIPTION
                 "Each entry records information about one CLNP end system
                 ID destination known to the Intermediate System."
             INDEX {  isisL1CLNPRouteMetQOS,			-- 02new
                      isisL1CLNPRouteDest,			-- 02new
                      isisL1CLNPRouteForw }
             ::= { isisL1CLNPDestTable 1 }

          IsisL1CLNPDestEntry ::=
             SEQUENCE {
                isisL1CLNPRouteDest
                   SystemID,
                isisL1CLNPRouteMetQOS
                   TOS,
                isisL1CLNPRouteMetric
                   PathCost,
                isisL1CLNPRouteForw
                   OBJECT IDENTIFIER,
                isisL1CLNPRouteSource
                   INTEGER,
                isisL1CLNPSysInstance
                   INTEGER
             }

          isisL1CLNPRouteDest OBJECT-TYPE
             SYNTAX SystemID
             ACCESS read-only
             STATUS mandatory
             DESCRIPTION
                 "The destination end system ID."
             ::= { isisL1CLNPDestEntry 1 }

          isisL1CLNPRouteMetQOS OBJECT-TYPE
             SYNTAX TOS
             ACCESS read-only
             STATUS mandatory
             DESCRIPTION
                 "The QOS metric for this destination."
             ::= { isisL1CLNPDestEntry 2 }

          isisL1CLNPRouteMetric OBJECT-TYPE
             SYNTAX PathCost
             ACCESS read-only
             STATUS mandatory
             DESCRIPTION
                 "The path metric value for this destination."
             ::= { isisL1CLNPDestEntry 3 }

          isisL1CLNPRouteForw OBJECT-TYPE
             SYNTAX OBJECT IDENTIFIER
             ACCESS read-only
             STATUS mandatory
             DESCRIPTION
                 "The OBJECT IDENTIFIER for the first object in the table
                 entry which corresponds to the entry used for forwarding
                 packets to this destination. This value is an OBJECT
                 IDENTIFIER for an instance of the object:
                 isisESAdjSysInstance or isisISAdjSysInstance."	   -- 02new
             ::= { isisL1CLNPDestEntry 4 }

          isisL1CLNPRouteSource OBJECT-TYPE
             SYNTAX   INTEGER {
                         manual (1),
                         level1 (2),
                         esis(3)
                      }
             ACCESS read-only
             STATUS mandatory
             DESCRIPTION
                 "The source of the destination. Manual is used if the
                 source is manually configured information on the system.
                 Level1 is used if the source is Level 1 LSPs. Esis is
                 used if the source is ES Hellos"
             ::= { isisL1CLNPDestEntry 5 }

          isisL1CLNPSysInstance OBJECT-TYPE
             SYNTAX INTEGER
             ACCESS read-write
             STATUS mandatory
             DESCRIPTION
                 "If the value of isisL1CLNPRouteSource is manual or
                 level1 then this is the identifier of the Integrated
                 IS-IS Level 1 instance from which this reachability
                 information was learned, otherwise this value is zero."
             ::= { isisL1CLNPDestEntry 6 }




          -- The Level 2 CLNP Destination Group

          -- The Level 2 CLNP Destination Group is present if the system
          -- supports Level 2 and forwards ISO 8473 packets.


          -- The Level 2 CLNP Destination Table

          -- The Level 2 CLNP Destination Table records information about
          -- each NSAP Address Prefix known to the Intermediate
          -- System

          isisL2CLNPDestTable OBJECT-TYPE
             SYNTAX SEQUENCE OF IsisL2CLNPDestEntry
             ACCESS not-accessible
             STATUS mandatory
             DESCRIPTION
                 "The Level 2 CLNP Destination Table records information
                 about each NSAP Address Prefix known to the Intermediate
                 System."
             ::= { isisCLNPDest 2 }

          isisL2CLNPDestEntry OBJECT-TYPE
             SYNTAX IsisL2CLNPDestEntry
             ACCESS not-accessible
             STATUS mandatory
             DESCRIPTION
                 "Each entry records information about one NSAP Address
                 Prefix known to the Intermediate System."
             INDEX {  isisL2CLNPRouteMetQOS,			-- 02new
                      isisL2CLNPRouteDest,			-- 02new
                      isisL2CLNPRouteForw }
             ::= { isisL2CLNPDestTable 1 }

          IsisL2CLNPDestEntry ::=
             SEQUENCE {
                isisL2CLNPRouteDest
                   NSAPPrefix,
                isisL2CLNPRouteMetQOS
                   TOS,
                isisL2CLNPRouteMetType
                   INTEGER,
                isisL2CLNPRouteIntMetric
                   PathCost,
                isisL2CLNPRouteExtMetric
                   INTEGER,
                isisL2CLNPRouteForw
                   OBJECT IDENTIFIER,
                isisL2CLNPRouteSource
                   INTEGER,
                isisL2CLNPSysInstance
                   INTEGER
             }

          isisL2CLNPRouteDest OBJECT-TYPE
             SYNTAX NSAPPrefix
             ACCESS read-only
             STATUS mandatory
             DESCRIPTION
                 "The destination address prefix."
             ::= { isisL2CLNPDestEntry 1 }

          isisL2CLNPRouteMetQOS OBJECT-TYPE
             SYNTAX TOS
             ACCESS read-only
             STATUS mandatory
             DESCRIPTION
                 "The QOS metric for this destination."
             ::= { isisL2CLNPDestEntry 2 }

          isisL2CLNPRouteMetType OBJECT-TYPE
             SYNTAX   INTEGER  {
                         internal (1),
                         external (2)
                      }
             ACCESS read-only
             STATUS mandatory
             DESCRIPTION
                 "Indicates whether the metric has an external component
                 or not"
             ::= { isisL2CLNPDestEntry 3 }

          isisL2CLNPRouteIntMetric OBJECT-TYPE
             SYNTAX PathCost
             ACCESS read-only
             STATUS mandatory
             DESCRIPTION
                 "The Internal path metric value for this destination."
             ::= { isisL2CLNPDestEntry 4 }

          isisL2CLNPRouteExtMetric OBJECT-TYPE
             SYNTAX INTEGER (0..63)
             ACCESS read-only
             STATUS mandatory
             DESCRIPTION
                 "The External metric value for this destination. If the
                 metric type is internal then this value is zero."
             ::= { isisL2CLNPDestEntry 5 }

          isisL2CLNPRouteForw OBJECT-TYPE
             SYNTAX OBJECT IDENTIFIER
             ACCESS read-only
             STATUS mandatory
             DESCRIPTION
                 "The OBJECT IDENTIFIER for the first object in the table
                 entry which corresponds to the entry used for forwarding
                 packets to this destination. This value is an OBJECT
                 IDENTIFIER for an instance of one of the following
                 objects: isisVirtSysInstance, isisISAdjSysInstance,
                 isisRASysInstance."
             ::= { isisL2CLNPDestEntry 6 }

          isisL2CLNPRouteSource OBJECT-TYPE
             SYNTAX   INTEGER {
                         manual (1),
                         level2 (2)
                      }
             ACCESS read-only
             STATUS mandatory
             DESCRIPTION
                 "The source of the destination. Manual is used if the
                 source is manually configured information on the system.
                 Level2 is used if the source is Level 2 LSPs."
             ::= { isisL2CLNPDestEntry 7 }

          isisL2CLNPSysInstance OBJECT-TYPE
             SYNTAX INTEGER
             ACCESS read-write
             STATUS mandatory
             DESCRIPTION
                 "The identifier of the Integrated IS-IS Level 2 instance
                 from which this reachability information was learned."
             ::= { isisL2CLNPDestEntry 8 }



          -- The IP Destination Group

          -- The IP Destination Group is present if the system forwards
          -- IP packets.


          -- The IP Destination Table

          -- The IP Destination Table records information about each
          -- destination known to the Intermediate System

          isisIPDestTable OBJECT-TYPE
             SYNTAX SEQUENCE OF IsisIPDestEntry
             ACCESS not-accessible
             STATUS mandatory
             DESCRIPTION
                 "The IP Destination Table records information about each
                 destination known to the Intermediate System."
             ::= { isisIPDest 1 }

          isisIPDestEntry OBJECT-TYPE
             SYNTAX IsisIPDestEntry
             ACCESS not-accessible
             STATUS mandatory
             DESCRIPTION
                 "Each entry records information about one IP destination
                 known to the Intermediate System."
             INDEX {  isisIPRouteMetTOS,			-- 02new
                      isisIPRouteDest,				
                      isisIPRouteMask,				
                      isisIPRouteForw }
             ::= { isisIPDestTable 1 }

          IsisIPDestEntry ::=
             SEQUENCE {
                isisIPRouteDest
                   IpAddress,
                isisIPRouteMask
                   IpAddress,
                isisIPRouteMetTOS
                   TOS,
                isisIPRouteMetType
                   INTEGER,
                isisIPRouteIntMetric
                   PathCost,
                isisIPRouteExtMetric
                   INTEGER,
                isisIPRouteForw
                   OBJECT IDENTIFIER,
                isisIPRouteSource
                   INTEGER,
                isisIPRouteSysInstance
                   INTEGER
             }

          isisIPRouteDest OBJECT-TYPE
             SYNTAX IpAddress
             ACCESS read-only
             STATUS mandatory
             DESCRIPTION
                 "The destination IP Address."
             ::= { isisIPDestEntry 1 }

          isisIPRouteMask OBJECT-TYPE
             SYNTAX IpAddress
             ACCESS read-only
             STATUS mandatory
             DESCRIPTION
                 "The mask for the isisIPRouteDest value."
             ::= { isisIPDestEntry 2 }

          isisIPRouteMetTOS OBJECT-TYPE
             SYNTAX TOS
             ACCESS read-only
             STATUS mandatory
             DESCRIPTION
                 "The TOS of the metric for this destination."
             ::= { isisIPDestEntry 3 }

          isisIPRouteMetType OBJECT-TYPE
             SYNTAX   INTEGER  {
                         internal (1),
                         external (2)
                      }
             ACCESS read-only
             STATUS mandatory
             DESCRIPTION
                 "Indicates whether the metric includes an external
                 component or not."
             ::= { isisIPDestEntry 4 }

          isisIPRouteIntMetric OBJECT-TYPE
             SYNTAX PathCost
             ACCESS read-only
             STATUS mandatory
             DESCRIPTION
                 "The internal path metric value for this destination."
             ::= { isisIPDestEntry 5 }

          isisIPRouteExtMetric OBJECT-TYPE
             SYNTAX INTEGER (0..63)
             ACCESS read-only
             STATUS mandatory
             DESCRIPTION
                 "The external metric value for this destination. If the
                 metric type is internal then this value is zero."
             ::= { isisIPDestEntry 6 }

          isisIPRouteForw OBJECT-TYPE
             SYNTAX OBJECT IDENTIFIER
             ACCESS read-only
             STATUS mandatory
             DESCRIPTION
                 "The OBJECT IDENTIFIER for the first object in the table
                 entry which corresponds to the entry used for forwarding
                 packets to this destination. This value is either an
                 OBJECT IDENTIFIER for an instance of one of the following
                 objects: isisL2SummAddrSysInstance, isisVirtSysInstance,
                 isisISAdjSysInstance, isisIPRASysInstance."
             ::= { isisIPDestEntry 7 }

          isisIPRouteSource OBJECT-TYPE
             SYNTAX   INTEGER {
                         manual (1),
                         level1 (2),
                         level2 (3)
                      }
             ACCESS read-only
             STATUS mandatory
             DESCRIPTION
                 "The source of the destination. Manual is used if the
                 source is manually configured information on the system.
                 Level1 is used if the source is Level 1 LSPs. Level2 is
                 used if the source is Level 2 LSPs."
             ::= { isisIPDestEntry 8 }

          isisIPRouteSysInstance OBJECT-TYPE
             SYNTAX INTEGER
             ACCESS read-write
             STATUS mandatory
             DESCRIPTION
                 "The identifier of the Integrated IS-IS instance from
                 which this reachability information was learned."
             ::= { isisIPDestEntry 9 }


	  -- The Test Group

	  -- This group of objects is for obtaining ISIS variables for testing 
	  -- purposes.

	  -- The Level 1 LSP Database Table

	  -- The Level 1 LSP Database Table contains one row for each Level 1 LSP
	  -- Database entry.

	  isisTestL1LSPDbaseTable OBJECT-TYPE
	     SYNTAX SEQUENCE OF IsisTestL1LSPDbaseEntry
	     ACCESS not-accessible
	     STATUS mandatory
	     DESCRIPTION
		 "Describe it"
	     ::= { isisTest 1 }

	  isisL1LSPDbaseEntry OBJECT-TYPE
	     SYNTAX IsisTestL1LSPDbaseEntry
	     ACCESS not-accessible
	     STATUS mandatory
	     DESCRIPTION
		 "Describe it"
	     ::= { isisTestL1LSPDbaseTable 1 }	     

	  IsisTestL1LSPDbaseEntry ::=
	     SEQUENCE {
		isisL1LSPIndex
		   INTEGER,
		isisL1LSPLinkForw
		   INTEGER,
		isisL1LSPLinkBack
		   INTEGER,
	        isisL1LSPSigIdSourceId
		   OCTET STRING,
	        isisL1LSPSigIdPseudonodeID
		   INTEGER,
	        isisL1LSPSigIdLSPNum
		   INTEGER,
	        isisL1LSPSigSeqNum
		   INTEGER,
	        isisL1LSPSigLifeTime
		   INTEGER,
	        isisL1LSPSigLevel
		   INTEGER,
	        isisL1LSPSigChecksum
		   INTEGER,
	        isisL1LSPOrigLifeTime
		   INTEGER,
	        isisL1LSPRemainTime
		   INTEGER,
	        isisL1LSPArrivalTimestamp
		   INTEGER,
	        isisL1LSPSRM
		   OCTET STRING,
	        isisL1LSPSSN
		   OCTET STRING,
		isisL1LSPFoundInSNP
		   INTEGER,
		isisL1LSPOnDeletedList
		   INTEGER,
		isisL1LSPBuf
		   OCTET STRING,
		isisL1LSPLen
		   INTEGER,
		isisL1LSPDesc
		   INTEGER,
		isisL1LSPHashNext
		   INTEGER,
		isisL1LSPSortNext
		   INTEGER
	     }

	  isisL1LSPIndex OBJECT-TYPE
	     SYNTAX INTEGER
	     ACCESS read-only
	     STATUS mandatory
	     DESCRIPTION
		 "Describe it"
	     ::= { isisL1LSPDbaseEntry 1 }

  	  isisL1LSPLinkForw OBJECT-TYPE
	     SYNTAX INTEGER
	     ACCESS read-only
	     STATUS mandatory
	     DESCRIPTION
		 "Describe it"
	     ::= { isisL1LSPDbaseEntry 2 }

	  isisL1LSPLinkBack OBJECT-TYPE
	     SYNTAX INTEGER
	     ACCESS read-only
	     STATUS mandatory
	     DESCRIPTION
		 "Describe it"
	     ::= { isisL1LSPDbaseEntry 3 }

	  isisL1LSPSigIdSourceId OBJECT-TYPE
	     SYNTAX OCTET STRING (SIZE(6))
	     ACCESS read-only
	     STATUS mandatory
	     DESCRIPTION
		 "Describe it"
	     ::= { isisL1LSPDbaseEntry 4 }

	  isisL1LSPSigIdPseudonodeID OBJECT-TYPE
	     SYNTAX INTEGER
	     ACCESS read-only
	     STATUS mandatory
	     DESCRIPTION
		 "Describe it"
	     ::= { isisL1LSPDbaseEntry 5 }

	  isisL1LSPSigIdLSPNum OBJECT-TYPE
	     SYNTAX INTEGER
	     ACCESS read-only
	     STATUS mandatory
	     DESCRIPTION
		 "Describe it"
	     ::= { isisL1LSPDbaseEntry 6 }

	  isisL1LSPSigSeqNum OBJECT-TYPE
	     SYNTAX INTEGER
	     ACCESS read-only
	     STATUS mandatory
	     DESCRIPTION
		 "Describe it"
	     ::= { isisL1LSPDbaseEntry 7 }

	  isisL1LSPSigLifeTime OBJECT-TYPE
	     SYNTAX INTEGER
	     ACCESS read-only
	     STATUS mandatory
	     DESCRIPTION
		 "Describe it"
	     ::= { isisL1LSPDbaseEntry 8 }

	  isisL1LSPSigLevel OBJECT-TYPE
	     SYNTAX INTEGER
	     ACCESS read-only
	     STATUS mandatory
	     DESCRIPTION
		 "Describe it"
	     ::= { isisL1LSPDbaseEntry 9 }

	  isisL1LSPSigChecksum OBJECT-TYPE
	     SYNTAX INTEGER
	     ACCESS read-only
	     STATUS mandatory
	     DESCRIPTION
		 "Describe it"
	     ::= { isisL1LSPDbaseEntry 10 }

	  isisL1LSPOrigLifeTime OBJECT-TYPE
	     SYNTAX INTEGER
	     ACCESS read-only
	     STATUS mandatory
	     DESCRIPTION
		 "Describe it"
	     ::= { isisL1LSPDbaseEntry 11 }

	  isisL1LSPRemainTime OBJECT-TYPE
	     SYNTAX INTEGER
	     ACCESS read-only
	     STATUS mandatory
	     DESCRIPTION
		 "Describe it"
	     ::= { isisL1LSPDbaseEntry 12 }

	  isisL1LSPArrivalTimestamp OBJECT-TYPE
	     SYNTAX INTEGER
	     ACCESS read-only
	     STATUS mandatory
	     DESCRIPTION
		 "Describe it"
	     ::= { isisL1LSPDbaseEntry 13 }

	  isisL1LSPSRM OBJECT-TYPE
	     SYNTAX OCTET STRING (SIZE(10))
	     ACCESS read-only
	     STATUS mandatory
	     DESCRIPTION
		 "Describe it"
	     ::= { isisL1LSPDbaseEntry 14 }

	  isisL1LSPSSN OBJECT-TYPE
	     SYNTAX OCTET STRING (SIZE(10))
	     ACCESS read-only
	     STATUS mandatory
	     DESCRIPTION
		 "Describe it"
	     ::= { isisL1LSPDbaseEntry 15 }

	  isisL1LSPFoundInSNP OBJECT-TYPE
	     SYNTAX INTEGER
	     ACCESS read-only
	     STATUS mandatory
	     DESCRIPTION
		 "Describe it"
	     ::= { isisL1LSPDbaseEntry 16 }

	  isisL1LSPOnDeletedList OBJECT-TYPE
	     SYNTAX INTEGER
	     ACCESS read-only
	     STATUS mandatory
	     DESCRIPTION
		 "Describe it"
	     ::= { isisL1LSPDbaseEntry 17 }

	  isisL1LSPBuf OBJECT-TYPE
	     SYNTAX OCTET STRING
	     ACCESS read-only
	     STATUS mandatory
	     DESCRIPTION
		 "Describe it"
	     ::= { isisL1LSPDbaseEntry 18 }

	  isisL1LSPLen OBJECT-TYPE
	     SYNTAX INTEGER
	     ACCESS read-only
	     STATUS mandatory
	     DESCRIPTION
		 "Describe it"
	     ::= { isisL1LSPDbaseEntry 19 }

	  isisL1LSPDesc OBJECT-TYPE
	     SYNTAX INTEGER
	     ACCESS read-only
	     STATUS mandatory
	     DESCRIPTION
		 "Describe it"
	     ::= { isisL1LSPDbaseEntry 20 }

	  isisL1LSPHashNext OBJECT-TYPE
	     SYNTAX INTEGER
	     ACCESS read-only
	     STATUS mandatory
	     DESCRIPTION
		 "Describe it"
	     ::= { isisL1LSPDbaseEntry 21 }

	  isisL1LSPSortNext OBJECT-TYPE
	     SYNTAX INTEGER
	     ACCESS read-only
	     STATUS mandatory
	     DESCRIPTION
		 "Describe it"
	     ::= { isisL1LSPDbaseEntry 22 }



	  -- The Level 2 LSP Database Table

	  -- The Level 2 LSP Database Table contains one row for each Level 2 LSP
	  -- Database entry.

	  isisTestL2LSPDbaseTable OBJECT-TYPE
	     SYNTAX SEQUENCE OF IsisTestL2LSPDbaseEntry
	     ACCESS not-accessible
	     STATUS mandatory
	     DESCRIPTION
		 "Describe it"
	     ::= { isisTest 2 }

	  isisL2LSPDbaseEntry OBJECT-TYPE
	     SYNTAX IsisTestL2LSPDbaseEntry
	     ACCESS not-accessible
	     STATUS mandatory
	     DESCRIPTION
		 "Describe it"
	     ::= { isisTestL2LSPDbaseTable 1 }	     

	  IsisTestL2LSPDbaseEntry ::=
	     SEQUENCE {
		isisL2LSPIndex
		   INTEGER,
		isisL2LSPLinkForw
		   INTEGER,
		isisL2LSPLinkBack
		   INTEGER,
	        isisL2LSPSigIdSourceId
		   OCTET STRING,
	        isisL2LSPSigIdPseudonodeID
		   INTEGER,
	        isisL2LSPSigIdLSPNum
		   INTEGER,
	        isisL2LSPSigSeqNum
		   INTEGER,
	        isisL2LSPSigLifeTime
		   INTEGER,
	        isisL2LSPSigLevel
		   INTEGER,
	        isisL2LSPSigChecksum
		   INTEGER,
	        isisL2LSPOrigLifeTime
		   INTEGER,
	        isisL2LSPRemainTime
		   INTEGER,
	        isisL2LSPArrivalTimestamp
		   INTEGER,
	        isisL2LSPSRM
		   OCTET STRING,
	        isisL2LSPSSN
		   OCTET STRING,
		isisL2LSPFoundInSNP
		   INTEGER,
		isisL2LSPOnDeletedList
		   INTEGER,
		isisL2LSPBuf
		   OCTET STRING,
		isisL2LSPLen
		   INTEGER,
		isisL2LSPDesc
		   INTEGER,
		isisL2LSPHashNext
		   INTEGER,
		isisL2LSPSortNext
		   INTEGER
	     }

	  isisL2LSPIndex OBJECT-TYPE
	     SYNTAX INTEGER
	     ACCESS read-only
	     STATUS mandatory
	     DESCRIPTION
		 "Describe it"
	     ::= { isisL2LSPDbaseEntry 1 }

  	  isisL2LSPLinkForw OBJECT-TYPE
	     SYNTAX INTEGER
	     ACCESS read-only
	     STATUS mandatory
	     DESCRIPTION
		 "Describe it"
	     ::= { isisL2LSPDbaseEntry 2 }

	  isisL2LSPLinkBack OBJECT-TYPE
	     SYNTAX INTEGER
	     ACCESS read-only
	     STATUS mandatory
	     DESCRIPTION
		 "Describe it"
	     ::= { isisL2LSPDbaseEntry 3 }

	  isisL2LSPSigIdSourceId OBJECT-TYPE
	     SYNTAX OCTET STRING (SIZE(6))
	     ACCESS read-only
	     STATUS mandatory
	     DESCRIPTION
		 "Describe it"
	     ::= { isisL2LSPDbaseEntry 4 }

	  isisL2LSPSigIdPseudonodeID OBJECT-TYPE
	     SYNTAX INTEGER
	     ACCESS read-only
	     STATUS mandatory
	     DESCRIPTION
		 "Describe it"
	     ::= { isisL2LSPDbaseEntry 5 }

	  isisL2LSPSigIdLSPNum OBJECT-TYPE
	     SYNTAX INTEGER
	     ACCESS read-only
	     STATUS mandatory
	     DESCRIPTION
		 "Describe it"
	     ::= { isisL2LSPDbaseEntry 6 }

	  isisL2LSPSigSeqNum OBJECT-TYPE
	     SYNTAX INTEGER
	     ACCESS read-only
	     STATUS mandatory
	     DESCRIPTION
		 "Describe it"
	     ::= { isisL2LSPDbaseEntry 7 }

	  isisL2LSPSigLifeTime OBJECT-TYPE
	     SYNTAX INTEGER
	     ACCESS read-only
	     STATUS mandatory
	     DESCRIPTION
		 "Describe it"
	     ::= { isisL2LSPDbaseEntry 8 }

	  isisL2LSPSigLevel OBJECT-TYPE
	     SYNTAX INTEGER
	     ACCESS read-only
	     STATUS mandatory
	     DESCRIPTION
		 "Describe it"
	     ::= { isisL2LSPDbaseEntry 9 }

	  isisL2LSPSigChecksum OBJECT-TYPE
	     SYNTAX INTEGER
	     ACCESS read-only
	     STATUS mandatory
	     DESCRIPTION
		 "Describe it"
	     ::= { isisL2LSPDbaseEntry 10 }

	  isisL2LSPOrigLifeTime OBJECT-TYPE
	     SYNTAX INTEGER
	     ACCESS read-only
	     STATUS mandatory
	     DESCRIPTION
		 "Describe it"
	     ::= { isisL2LSPDbaseEntry 11 }

	  isisL2LSPRemainTime OBJECT-TYPE
	     SYNTAX INTEGER
	     ACCESS read-only
	     STATUS mandatory
	     DESCRIPTION
		 "Describe it"
	     ::= { isisL2LSPDbaseEntry 12 }

	  isisL2LSPArrivalTimestamp OBJECT-TYPE
	     SYNTAX INTEGER
	     ACCESS read-only
	     STATUS mandatory
	     DESCRIPTION
		 "Describe it"
	     ::= { isisL2LSPDbaseEntry 13 }

	  isisL2LSPSRM OBJECT-TYPE
	     SYNTAX OCTET STRING (SIZE(10))
	     ACCESS read-only
	     STATUS mandatory
	     DESCRIPTION
		 "Describe it"
	     ::= { isisL2LSPDbaseEntry 14 }

	  isisL2LSPSSN OBJECT-TYPE
	     SYNTAX OCTET STRING (SIZE(10))
	     ACCESS read-only
	     STATUS mandatory
	     DESCRIPTION
		 "Describe it"
	     ::= { isisL2LSPDbaseEntry 15 }

	  isisL2LSPFoundInSNP OBJECT-TYPE
	     SYNTAX INTEGER
	     ACCESS read-only
	     STATUS mandatory
	     DESCRIPTION
		 "Describe it"
	     ::= { isisL2LSPDbaseEntry 16 }

	  isisL2LSPOnDeletedList OBJECT-TYPE
	     SYNTAX INTEGER
	     ACCESS read-only
	     STATUS mandatory
	     DESCRIPTION
		 "Describe it"
	     ::= { isisL2LSPDbaseEntry 17 }

	  isisL2LSPBuf OBJECT-TYPE
	     SYNTAX OCTET STRING
	     ACCESS read-only
	     STATUS mandatory
	     DESCRIPTION
		 "Describe it"
	     ::= { isisL2LSPDbaseEntry 18 }

	  isisL2LSPLen OBJECT-TYPE
	     SYNTAX INTEGER
	     ACCESS read-only
	     STATUS mandatory
	     DESCRIPTION
		 "Describe it"
	     ::= { isisL2LSPDbaseEntry 19 }

	  isisL2LSPDesc OBJECT-TYPE
	     SYNTAX INTEGER
	     ACCESS read-only
	     STATUS mandatory
	     DESCRIPTION
		 "Describe it"
	     ::= { isisL2LSPDbaseEntry 20 }

	  isisL2LSPHashNext OBJECT-TYPE
	     SYNTAX INTEGER
	     ACCESS read-only
	     STATUS mandatory
	     DESCRIPTION
		 "Describe it"
	     ::= { isisL2LSPDbaseEntry 21 }

	  isisL2LSPSortNext OBJECT-TYPE
	     SYNTAX INTEGER
	     ACCESS read-only
	     STATUS mandatory
	     DESCRIPTION
		 "Describe it"
	     ::= { isisL2LSPDbaseEntry 22 }


          END

          -- End of Object Definitions
